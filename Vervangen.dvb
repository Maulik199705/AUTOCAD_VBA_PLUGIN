Attribute VB_Name = "Module1"
Option Explicit
Sub vv()
frmvervangen.show
End Sub
Sub zx()
frmpdf.show
End Sub
Sub lr()
frmRenLayer.show
End Sub
Sub fm()
frmverwijder.show
End Sub
Sub pd()
frmpdf.show
End Sub

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
Option Explicit
Private Sub AcadDocument_BeginClose()
Dim element
Dim SYMBOOL
Dim ATTRIBUTEN: Dim ATTRIBUUT: Dim zz: Dim rol
Dim i
For Each element In ThisDrawing.ModelSpace
        If element.ObjectName = "AcDbBlockReference" Then
            If UCase(element.Name) = "GROEPTEKSTBLOKNEW" Then
                Set SYMBOOL = element
                If SYMBOOL.HasAttributes Then
                    ATTRIBUTEN = SYMBOOL.GetAttributes
                    For i = LBound(ATTRIBUTEN) To UBound(ATTRIBUTEN)
                    Set ATTRIBUUT = ATTRIBUTEN(i)
                      If ATTRIBUUT.TagString = "FLEXFIX" And UCase(ATTRIBUUT.TextString) = "JA" Then
                       frmflexfixexport.show
                       Exit Sub
                      End If
                    Next i
                End If
            End If
        End If
        Next element

End Sub
Sub revi()
Dim ELEMENT700
Dim INSP700
Dim PE700(0 To 2) As Double
Dim NAAMBLOK700
NAAMBLOK700 = "C:\ACAD2002\DWG\REVISIEBLOK.DWG"
Dim OP
Dim OP1
Dim ATTRIBUUT: Dim BLOCKREFOBJ: Dim SYMBOOL: Dim ATTRIBUTEN: Dim x

 For Each ELEMENT700 In ThisDrawing.ModelSpace
             If ELEMENT700.ObjectName = "AcDbBlockReference" Then
                If UCase(ELEMENT700.Name) = "KADERLOGO" Then
'''                  Set SYMBOOL = ELEMENT700
'''                  If SYMBOOL.HasAttributes Then
'''                  ATTRIBUTEN = SYMBOOL.GetAttributes
'''                    For X = LBound(ATTRIBUTEN) To UBound(ATTRIBUTEN)
'''                    Set ATTRIBUUT = ATTRIBUTEN(X)
'''                        If ATTRIBUUT.TagString = "SCHAAL" Then
'''                        OP = ATTRIBUUT.TextString
'''                        If OP = "1:50" Then OP1 = 1
'''                        If OP = "1:100" Then OP1 = 0.5
'''                        If OP = "1:200" Then OP1 = 0.25
                        INSP700 = ELEMENT700.InsertionPoint
                        PE700(0) = INSP700(0) - 882
                        PE700(1) = INSP700(1) + 329
                        PE700(2) = 0
                        Set BLOCKREFOBJ = ThisDrawing.ModelSpace.InsertBlock(PE700, NAAMBLOK700, 1, 1, 1, 0)
                        End If
''                     Next X
''                   End If
''                 End If
              End If
              Update
Next ELEMENT700
End Sub
Sub vervangen()
  
  Call frmvervangen.show(vbModal)

End Sub
Sub translate()
  
  Call frmRenLayer.show(vbModal)

End Sub
Sub blokplot()
  ' blokfiles plotten bogro tekeningen, bloks opzoeken, filteren op naam en dan een A4 printje maken
  
    Dim dwgnm
    Dim drawing As AcadDocument
''    For Each drawing In ThisDrawing.Application.Documents
''        drawing.Activate
        
        Dim controle1
        Dim controle2
        Dim controle3
        Dim controle4
        
        
        Dim pe1(0 To 2) As Double
        Dim PE2(0 To 2) As Double
        Dim pe10(0 To 2) As Double
        Dim pe11(0 To 2) As Double
        Dim pe12(0 To 2) As Double
        Dim pe6(0 To 2) As Double
        Dim insp
        Dim pe3 As String
        Dim pe4 As String
        Dim pe30 As String
        Dim pe40 As String
        
        Dim element As Object
        For Each element In ThisDrawing.ModelSpace
              If element.ObjectName = "AcDbBlockReference" Then
                  controle1 = InStr(1, element.Name, "h0.kl.1", vbTextCompare)
                  controle2 = InStr(1, element.Name, "h1.kl.1", vbTextCompare)
                  controle3 = InStr(1, element.Name, "h2.kl.1", vbTextCompare)
                  'a''controle4 = InStr(1, element.Name, "h3.kl.1", vbTextCompare)
                   
                  
                  If controle1 <> 0 Or controle2 <> 0 Or controle3 <> 0 Or controle4 <> 0 Then
                    insp = element.InsertionPoint
                  pe1(0) = insp(0) + 7000
                  pe1(1) = insp(1) + 10000
                  pe1(2) = 0
                  
                  PE2(0) = insp(0) - 7000
                  PE2(1) = insp(1) - 10000
                  PE2(2) = 0
                  
                  pe6(0) = insp(0)
                  pe6(1) = insp(1)
                  pe6(2) = 0
 
                  
                  pe3 = pe1(0) & "," & pe1(1)
                  pe4 = PE2(0) & "," & PE2(1)
                  'MsgBox pe3
                  
        
                  'ThisDrawing.SendCommand "text" & vbCr & pe4 & vbCr & "100" & vbCr & "90" & vbCr & dwgnm & vbCr
                  'a''ThisDrawing.SendCommand "-plot" & vbCr & "Y" & vbCr & "Model" & vbCr & "\\FSERVER2\P39 L2100TN" & vbCr & "A4" & vbCr & "M" & vbCr & "P" & vbCr & "N" & vbCr & "W" & vbCr & pe3 & vbCr & pe4 & vbCr & "F" & vbCr & "0,0" & vbCr & "Y" & vbCr & "wth.ctb" & vbCr & "Y" & vbCr & "N" & vbCr & "N" & vbCr & "Y" & vbCr & "Y" & vbCr
                 
                  pe10(0) = PE2(0) + 300000
                  pe10(1) = PE2(1)
                  pe10(2) = 0
                    
                  pe11(0) = pe10(0) + 308000
                  pe11(1) = pe10(1) + 140000
                  pe11(2) = 0
                  
'''                  pe11(0) = pe2(0) + 8000
'''                  pe11(1) = pe2(1) + 140000
'''                  pe11(2) = 0
                  
                  element.Move PE2, pe10
                  pe30 = pe10(0) & "," & pe10(1)
                  pe40 = pe11(0) & "," & pe11(1)
                  
                  ThisDrawing.SendCommand "copyclip" & vbCr & "W" & vbCr & pe30 & vbCr & pe40 & vbCr & vbCr
                  dwgnm = ThisDrawing.GetVariable("dwgname")
                  Dim textObj As AcadText
                  ''Set textObj = ThisDrawing.ModelSpace.AddText(dwgnm, pe10, 100)
                  
                  
        ''          Set blockRefObj = ThisDrawing.ModelSpace.InsertBlock(insp, naamblok, 1, 1, 1, 0)
                  End If
                
                End If
             Next element
          
          Dim dwgnm2
          Dim check2
          dwgnm2 = ThisDrawing.GetVariable("dwgname")
          check2 = Split(dwgnm2, " ")
          Dim check3
          check3 = check2(2)
          
          ThisDrawing.Application.Documents.Add ("Autocad.dwt")
          
          ThisDrawing.SendCommand "pasteclip" & vbCr & "0,0" & vbCr
    
        
        'Zoom all
        
''    Next drawing
Call verder(check3)
End Sub
Sub verder(check3)
        
        Dim controle100
        Dim controle200
        Dim controle300
        Dim controle400
        Dim dw
        dw = "c:\acad2002\"
        Dim dw1
        dw1 = dw & check3 & ".dwg"
        
        Dim pe100(0 To 2) As Double
        Dim pe200(0 To 2) As Double
        Dim insp100
        Dim insp200
                
        Dim element As Object
        For Each element In ThisDrawing.ModelSpace
              If element.ObjectName = "AcDbBlockReference" Then
                  ''controle1 = InStr(1, element.Name, "h0.kl.1", vbTextCompare)
                  controle200 = InStr(1, element.Name, "h1.kl.1", vbTextCompare)
                  controle300 = InStr(1, element.Name, "h2.kl.1", vbTextCompare)
                  'a''controle4 = InStr(1, element.Name, "h3.kl.1", vbTextCompare)
                   
                  
                  If controle200 <> 0 Then
                   insp100 = element.InsertionPoint
                  
                  pe100(0) = insp100(0) + 10000
                  pe100(1) = insp100(1) - 39500
                  pe100(2) = 0
                  
                  element.Move insp100, pe100
                  End If
                  
                  
                  If controle300 <> 0 Then
                   insp200 = element.InsertionPoint
                  
                  pe200(0) = insp200(0) + 20000
                  pe200(1) = insp200(1) - 79000
                  pe200(2) = 0
                  
                  element.Move insp200, pe200
                  End If
                
                
                End If
        Next element
        
        
        
          ZoomAll
          ThisDrawing.SendCommand "scale" & vbCr & "all" & vbCr & vbCr & "0,0" & vbCr & "0.1" & vbCr
          
          
         ' ThisDrawing.SaveAs (dw1)
         ' ThisDrawing.Application.Documents.Close
End Sub
Sub delhatch()
  ' plotfile aanmaken voor alle openstaande tekeningen
  

  
    Dim drawing As AcadDocument
    For Each drawing In ThisDrawing.Application.Documents
        drawing.Activate
        
'''          ThisDrawing.SendCommand "burst" & vbCr & "all" & vbCr & vbCr
'''            ThisDrawing.SendCommand "burst" & vbCr & "all" & vbCr & vbCr
'''            ThisDrawing.SendCommand "burst" & vbCr & "all" & vbCr & vbCr

        ThisDrawing.SendCommand "-layer" & vbCr & "Freeze" & vbCr & "AA$1A---VERBLIJFSGEBIED" & vbCr & vbCr
'''''        Dim layer
'''''        Dim entHandle As String
'''''        Dim entry As AcadEntity
'''''        For Each entry In ThisDrawing.ModelSpace
'''''            entHandle = entry.ObjectName
'''''            entry.Highlight (True)
'''''            entry.Highlight (False)
'''''            If entHandle = "AcDbHatch" Then entry.Delete
'''''            If entHandle = "AcDbSolid" Then entry.Delete
'''''            Update
'''''        Next
        
        
        
        ThisDrawing.Save
        ThisDrawing.Close
        
    Next drawing
End Sub
Sub ops()
'''    Dim drawing As AcadDocument
'''    For Each drawing In ThisDrawing.Application.Documents
'''    drawing.Activate
On Error Resume Next
ThisDrawing.SendCommand "audit" & vbCr & "y" & vbCr
        
    Dim objBlock As AcadBlock
    Dim objEntity As AcadEntity
    Dim objLayer As AcadLayer
'      Dim mypos
'
'      For Each objBlock In ThisDrawing.Blocks
'        For Each objEntity In objBlock
'          mypos = InStr(1, objEntity, "STRAMIEN")
'          objEntity.layer = "STRAMIEN"
'          objEntity.color = acByLayer
'          objEntity.Lineweight = acLnWtByLwDefault
'        Next objEntity
'      Next objBlock
'      ThisDrawing.SendCommand "-layer" & vbCr & "Freeze" & vbCr & "STRAMIEN" & vbCr & vbCr

      
         
Dim olddata As String
olddata = ThisDrawing.GetVariable("clayer")
ThisDrawing.SendCommand "-layer" & vbCr & "M" & vbCr & "BOUWKUNDIG" & vbCr & vbCr
ThisDrawing.SendCommand "-layer" & vbCr & "M" & vbCr & "3" & vbCr & vbCr
ThisDrawing.SendCommand "-layer" & vbCr & "Set" & vbCr & olddata & vbCr & vbCr
Update




  
      'alles naar layer bouwkundig
      Dim object3
        For Each object3 In ThisDrawing.ModelSpace
           object3.layer = "bouwkundig"
        Next
       
       
'set all object colors to bylayer
      For Each objBlock In ThisDrawing.Blocks
        For Each objEntity In objBlock
          objEntity.layer = "bouwkundig"
          objEntity.color = acByLayer
          objEntity.Lineweight = acLnWtByLwDefault
        Next objEntity
      Next objBlock
      
      ThisDrawing.SendCommand "burst" & vbCr & "all" & vbCr & vbCr
      
      
Dim layer
Dim entHandle As String
    Dim entry As AcadEntity
    For Each entry In ThisDrawing.ModelSpace
        entHandle = entry.ObjectName
        entry.Highlight (True)
        'MsgBox "The handle of this object is " & entHandle, vbInformation, "Handle Example"
        entry.Highlight (False)
        If entHandle = "AcDbDimension" Then entry.Delete
        If entHandle = "AcDbHatch" Then entry.Delete
        If entHandle = "AcDbSolid" Then entry.Delete
        If entHandle = "AcDbRotatedDimension" Then entry.Delete
        If entHandle = "AcDbAlignedDimension" Then entry.Delete
        If entHandle = "AcDbAngularDimension" Then entry.Delete
        
        If entHandle = "AcDbText" Then
            entry.layer = "3"
            entry.color = acByLayer
            If InStr(1, entry.TextString, "merk", vbBinaryCompare) Then entry.Delete
            If InStr(1, entry.TextString, "MERK", vbBinaryCompare) Then entry.Delete
        End If
        If entHandle = "AcDbMText" Then
    
            If InStr(1, entry.TextString, "merk", vbBinaryCompare) Then entry.Delete
            If InStr(1, entry.TextString, "MERK", vbBinaryCompare) Then entry.Delete
            If UCase(entry.TextString) = "K." Then entry.Delete
            If UCase(entry.TextString) = "MV" Then entry.Delete
            If UCase(entry.TextString) = "HWA" Then entry.Delete
            If UCase(entry.TextString) = "H.W.A." Then entry.Delete
            If UCase(entry.TextString) = "WINDVERBAND" Then entry.Delete
            entry.layer = "3"
            entry.color = acByLayer
        End If
        If entHandle = "AcDbImage" Then entry.Delete
        Update
    Next



ThisDrawing.PurgeAll
ThisDrawing.SendCommand "wthlayer" & vbCr
ThisDrawing.Save

'''    Next drawing
End Sub

Attribute VB_Name = "frmRenLayer"
Attribute VB_Base = "0{1E810FA0-7BB6-4A43-9535-EA8B9C043B0F}{F390D9DD-8D6C-490C-AC9B-E22EB037B489}"
Attribute VB_GlobalNameSpace = False
Attribute VB_Creatable = False
Attribute VB_PredeclaredId = True
Attribute VB_Exposed = False
Attribute VB_TemplateDerived = False
Attribute VB_Customizable = False
Private mappAcad As AcadApplication
Private mstrPath As String

'09-09-2005 Legrichting bepalen
'M.Bosch en G.C.Haak

#If VBA7 Then
    Private Declare PtrSafe Function FindWindow Lib "user32" Alias "FindWindowA" (ByVal lpClassName As String, ByVal lpWindowName As String) As LongPtr
    Private Declare PtrSafe Function DrawMenuBar Lib "user32" (ByVal hWnd As LongPtr) As Long
    Private Declare PtrSafe Function GetMenuItemCount Lib "user32" (ByVal hMenu As LongPtr) As Long
    Private Declare PtrSafe Function GetSystemMenu Lib "user32" (ByVal hWnd As LongPtr, ByVal bRevert As Long) As LongPtr
    Private Declare PtrSafe Function RemoveMenu Lib "user32" (ByVal hMenu As LongPtr, ByVal nPosition As Long, ByVal wFlags As Long) As Long
#Else
    Private Declare Function FindWindow Lib "user32" Alias "FindWindowA" (ByVal lpClassName As String, ByVal lpWindowName As String) As Long
    Private Declare Function DrawMenuBar Lib "user32" (ByVal hWnd As Long) As Long
    Private Declare Function GetMenuItemCount Lib "user32" (ByVal hMenu As Long) As Long
    Private Declare Function GetSystemMenu Lib "user32" (ByVal hWnd As Long, ByVal bRevert As Long) As Long
    Private Declare Function RemoveMenu Lib "user32" (ByVal hMenu As Long, ByVal nPosition As Long, ByVal wFlags As Long) As Long
#End If

Private Const MF_BYPOSITION = &H400
Private Const MF_REMOVE = &H1000

Private Sub UserForm_Initialize()
#If VBA7 Then
    Dim lngHwnd As LongPtr
    Dim lngMenu As LongPtr
#Else
    Dim lngHwnd As Long
    Dim lngMenu As Long
#End If
Dim lngCnt As Long
Dim box1 As Variant

lngHwnd = FindWindow(vbNullString, Me.Caption)
lngMenu = GetSystemMenu(lngHwnd, 0)

If lngMenu Then
    lngCnt = GetMenuItemCount(lngMenu)
    RemoveMenu lngMenu, lngCnt - 1, MF_REMOVE Or MF_BYPOSITION
    DrawMenuBar lngHwnd
End If

box1 = ThisDrawing.GetVariable("angdir")

If box1 = 0 Then OptionButton1.Value = True
If box1 = 1 Then OptionButton2.Value = True
End Sub

Private Sub cmdAfsluiten_Click()
If OptionButton1.Value = True Then ThisDrawing.SetVariable "angdir", 0
If OptionButton2.Value = True Then ThisDrawing.SetVariable "angdir", 1
Unload Me
End Sub




Private Sub CommandButton1_Click()
On Error Resume Next
ListBox1.Clear
Dim laagobj As Object
Dim mystr
Dim MYSTR2
Dim MYSTR3
Dim MYSTR4
Dim UNITTEL
Dim UNITTEL2
Dim UNITTEL3
Dim UNITTEL5


UNITTEL = frmRenLayer.TextBox1
If UNITTEL > 0 And UNITTEL < 10 Then
   frmRenLayer.TextBox1 = "0" & frmRenLayer.TextBox1
End If
UNITTEL2 = frmRenLayer.TextBox2
UNITTEL3 = frmRenLayer.TextBox2
If UNITTEL2 > 0 And UNITTEL2 < 10 Then
   UNITTEL3 = "0" & frmRenLayer.TextBox2
   frmRenLayer.TextBox2 = "0" & frmRenLayer.TextBox2
End If



For Each laagobj In ThisDrawing.Layers
mystr = Split(laagobj.Name, " ")
'MYSTR(0) = GROEP
'MYSTR(1) = 01.01

If UCase(mystr(0)) = "GROEP" Then

    MYSTR3 = Split(mystr(1), ".")
    'MYSTR3(0) = 01
    'MYSTR3(1) = 01
    

    If MYSTR3(0) = Val(TextBox1) Then
    MYSTR4 = "groep " & UNITTEL3 & "." & MYSTR3(1)
    ListBox1.AddItem (MYSTR4)
    laagobj.Name = MYSTR4
    
    End If
End If
Next laagobj

Dim element2 As Object
 For Each element2 In ThisDrawing.ModelSpace
      If element2.ObjectName = "AcDbBlockReference" Then
      If UCase(element2.Name) = "GROEPTEKSTBLOKNEW" Then
      Set SYMBOOL = element2
       If SYMBOOL.HasAttributes Then
        ATTRIBUTEN = SYMBOOL.GetAttributes
        For i = LBound(ATTRIBUTEN) To UBound(ATTRIBUTEN)
        Set ATTRIBUUT = ATTRIBUTEN(i)
        If UCase(ATTRIBUUT.TagString) = "UNITNUMMER" Then
               rr = ATTRIBUUT.TextString
               If rr = frmRenLayer.TextBox1 Then
                      For Z = LBound(ATTRIBUTEN) To UBound(ATTRIBUTEN)
                      Set ATTRIBUUT = ATTRIBUTEN(Z)
                        If ATTRIBUUT.TagString = "GROEPTEKST" Then
                        TT = ATTRIBUUT.TextString
                        hh = Split(TT, ".")
                        ee = "groep " & frmRenLayer.TextBox2 & "." & hh(1)
                        ATTRIBUUT.TextString = ee
                               For Q = LBound(ATTRIBUTEN) To UBound(ATTRIBUTEN)
                               Set ATTRIBUUT = ATTRIBUTEN(Q)
                               If ATTRIBUUT.TagString = "UNITNUMMER" Then ATTRIBUUT.TextString = frmRenLayer.TextBox2
                               Next Q
                        End If
                      Next Z
               End If
         End If
     Next i
End If
End If
End If
Next element2
'Unload Me

Dim element22 As Object
 For Each element22 In ThisDrawing.ModelSpace
      If element22.ObjectName = "AcDbBlockReference" Then
      If UCase(element22.Name) = "MAT_SPE_ZD" Or UCase(element22.Name) = "MAT_SPE_PE" Or UCase(element22.Name) = "MAT_SPE_PE800" _
      Or UCase(element22.Name) = "MAT_SPE_ALU" Or UCase(element22.Name) = "MAT_SPE_ZDRINGLEIDING" _
      Or UCase(element22.Name) = "MAT_SPE_PERINGLEIDING" Or UCase(element22.Name) = "MAT_SPE_ALURINGLEIDING" _
      Or UCase(element22.Name) = "MAT_SPE_FLEX" Or UCase(element22.Name) = "MAT_SPE_FLEX_AANKOPPEL" Then
      Set SYMBOOL = element22
       If SYMBOOL.HasAttributes Then
        ATTRIBUTEN = SYMBOOL.GetAttributes
        For W = LBound(ATTRIBUTEN) To UBound(ATTRIBUTEN)
             Set ATTRIBUUT = ATTRIBUTEN(W)
               If UCase(ATTRIBUUT.TagString) = "RNU" Then
               rrs = ATTRIBUUT.TextString
               If rrs = frmRenLayer.TextBox1 Then ATTRIBUUT.TextString = frmRenLayer.TextBox2
               End If
        Next W
      End If
     End If
 End If
Next element22


For Each element222 In ThisDrawing.ModelSpace
      If element222.ObjectName = "AcDbBlockReference" Then
        If element222.Name = "HERZ" Or element222.Name = "RUH-R" Or element222.Name = "RUH-RT" _
        Or element222.Name = "RUB-R" Or element222.Name = "RUB-RT" Or element222.Name = "RUBK-R" Or element222.Name = "LT-VK" _
        Or element222.Name = "RUBK-RT" Or element222.Name = "LT" Or element222.Name = "LTS" Or element222.Name = "LT-N" Or element222.Name = "LTS-N" _
        Or element222.Name = "RUW" Or element222.Name = "RUV" Or element222.Name = "RUH-S" Or element222.Name = "VSKO-B" _
        Or element222.Name = "RUB-S" Or element222.Name = "KMV" Or element222.Name = "RUH-N" Or element222.Name = "RU-WW" Or element222.Name = "RINGLEIDING" _
        Or element222.Name = "RU-WWN" Or element222.Name = "RU-WWS" Or element222.Name = "RU-WKN" Or element222.Name = "RU-WKS" Then
      Set SYMBOOL = element222
        If SYMBOOL.HasAttributes Then
        ATTRIBUTEN = SYMBOOL.GetAttributes
        For u = LBound(ATTRIBUTEN) To UBound(ATTRIBUTEN)
        Set ATTRIBUUT = ATTRIBUTEN(u)
           If ATTRIBUUT.TagString = "UNITNUMMER" Then
               rrst = ATTRIBUUT.TextString
               If rrst = frmRenLayer.TextBox1 Then ATTRIBUUT.TextString = frmRenLayer.TextBox2
           End If
       
       Next u
      End If
     End If
     End If
   Next element222
Update

hern1 = "Regelunit " & TextBox1
hern2 = "Regelunit " & TextBox2
ThisDrawing.SendCommand "replacetext" & vbCr & hern1 & vbCr & hern2 & vbCr
frmRenLayer.Hide
Update
frmRenLayer.show

TextBox1 = Clear: TextBox2 = Clear
'''Dim Obj As AcadText
'''   For Each Obj In ThisDrawing.ModelSpace
'''        dd = "Regelunit " & frmRenLayer.TextBox1
'''        If Obj.TextString = dd Then Obj.TextString = "Regelunit " & frmRenLayer.TextBox2
'''   Next
End Sub
Private Sub TextBox1_Change()
If TextBox1.Text <> "" And TextBox2.Text <> "" Then
   CommandButton1.Enabled = True
   Else
   CommandButton1.Enabled = False
End If
End Sub

Private Sub TextBox2_Change()
If TextBox1.Text <> "" And TextBox2.Text <> "" Then
   CommandButton1.Enabled = True
   Else
   CommandButton1.Enabled = False
End If
End Sub
Private Sub cmdClose_Click()
Unload Me
End Sub

Attribute VB_Name = "frmSchtek"
Attribute VB_Base = "0{5940D7F9-16F5-49E4-A0B2-E9FD580A174D}{B6BC9038-7960-4430-8F1C-691014C7659C}"
Attribute VB_GlobalNameSpace = False
Attribute VB_Creatable = False
Attribute VB_PredeclaredId = True
Attribute VB_Exposed = False
Attribute VB_TemplateDerived = False
Attribute VB_Customizable = False
Private Sub CommandButton5_Click()
Dim element2

For Each element2 In ThisDrawing.ModelSpace
      If element2.Name = UCase("EXTERNAL REFERENCE") Then MsgBox "YEP"
Next element2
End Sub

Private Sub UserForm_Initialize()

ComboBox1.AddItem ("BOUWKUNDIG")
ComboBox1.AddItem ("ALGEMEEN")
ComboBox1.ListIndex = 0
  
End Sub

Private Sub CommandButton1_Click()
On Error Resume Next
UserForm1.Hide

Dim controle
Dim laagobj As AcadLayer
For Each laagobj In ThisDrawing.Layers
controle = InStr(1, laagobj.Name, UCase("STRAMIEN"), vbTextCompare)
If controle <> 0 Then
   laagobj.Name = "Stramien"
   laagobj.color = acRed
End If
Next laagobj

End Sub
Private Sub CommandButton3_Click()
Dim element2
For Each element2 In ThisDrawing.ModelSpace
      If element2.ObjectName = UCase("LWPOLYLINE") Then MsgBox "YEP"
Next element2
End Sub

Private Sub CommandButton4_Click()
Dim aa
aa = UCase(ComboBox1)
UserForm1.Hide





Dim controle
Dim laagobj As AcadLayer
For Each laagobj In ThisDrawing.Layers
controle = InStr(1, laagobj.Name, aa, vbTextCompare)
If controle <> 0 Then
   laagobj.Name = "Bouwkundig"
   laagobj.color = acByLayer
End If
Next laagobj


ThisDrawing.SendCommand "-layer" & vbCr & "Make" & vbCr & "3" & vbCr & vbCr
ThisDrawing.SendCommand "burst" & vbCr & "all" & vbCr & vbCr
ThisDrawing.SendCommand "burst" & vbCr & "all" & vbCr & vbCr
ThisDrawing.SendCommand "burst" & vbCr & "all" & vbCr & vbCr
Update

Dim layer
Dim entHandle As String
    Dim entry As AcadEntity
    For Each entry In ThisDrawing.ModelSpace
        entHandle = entry.ObjectName
        entry.Highlight (True)
        'MsgBox "The handle of this object is " & entHandle, vbInformation, "Handle Example"
        entry.Highlight (False)
        If entHandle = "AcDbDimension" Then entry.Delete
        If entHandle = "AcDbHatch" Then entry.Delete
        If entHandle = "AcDbSolid" Then entry.Delete
        If entHandle = "AcDbText" Then
            entry.layer = 3
            entry.color = acWhite
        End If
        If entHandle = "AcDbMText" Then
            entry.layer = 3
            entry.color = acWhite
        End If
        If entHandle = "AcDbImage" Then entry.Delete
        Update
    Next

ThisDrawing.SendCommand "-purge" & vbCr & "all" & vbCr & vbCr & "N" & vbCr
ThisDrawing.SendCommand "wthlayer" & vbCr
Unload Me
End Sub

Attribute VB_Name = "frmflexfixexport"
Attribute VB_Base = "0{868CEED7-2497-46BF-94CA-F0FADAD646B5}{05E5BFB4-C84A-4122-B358-80631B608865}"
Attribute VB_GlobalNameSpace = False
Attribute VB_Creatable = False
Attribute VB_PredeclaredId = True
Attribute VB_Exposed = False
Attribute VB_TemplateDerived = False
Attribute VB_Customizable = False
Private mappAcad As AcadApplication
Private mstrPath As String


#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
  'create acadapplication object
  Set mappAcad = GetObject(Class:="AutoCAD.Application")
End Sub
Private Sub cmdClose_Click()
Unload Me
End Sub
Private Sub CommandButton1_Click()
''For Each ELEMENT4 In ThisDrawing.ModelSpace
''        If ELEMENT4.ObjectName = "AcDbBlockReference" Then
''            If UCase(ELEMENT4.Name) = "GROEPTEKSTBLOKNEW" Then we = we + 1
''        End If
''Next
Dim element
Dim SYMBOOL
Dim ATTRIBUTEN: Dim ATTRIBUUT: Dim zz: Dim rol
Dim i: Dim J: Dim K: Dim aa: Dim bb: Dim cc: Dim dd: Dim ee:
Dim ff: Dim gg: Dim hh: Dim ii: Dim jj: Dim kk: Dim ll
Dim x
For Each element In ThisDrawing.ModelSpace
        
        If element.ObjectName = "AcDbBlockReference" Then
            If UCase(element.Name) = "GROEPTEKSTBLOKNEW" Then
                Set SYMBOOL = element
                If SYMBOOL.HasAttributes Then
                    ATTRIBUTEN = SYMBOOL.GetAttributes
                    For i = LBound(ATTRIBUTEN) To UBound(ATTRIBUTEN)
                    Set ATTRIBUUT = ATTRIBUTEN(i)
                      If ATTRIBUUT.TagString = "FLEXFIX" And UCase(ATTRIBUUT.TextString) = "JA" Then
                                   For x = LBound(ATTRIBUTEN) To UBound(ATTRIBUTEN)
                                   Set ATTRIBUUT = ATTRIBUTEN(x)
                                   If ATTRIBUUT.TagString = "ROLLENGTE" And ATTRIBUUT.TextString <> " " Then
                                        For J = LBound(ATTRIBUTEN) To UBound(ATTRIBUTEN)
                                        Set ATTRIBUUT = ATTRIBUTEN(J)
                                             If ATTRIBUUT.TagString = "UNITNUMMER" And ATTRIBUUT.TextString <> " " Then aa = ATTRIBUUT.TextString
                                             If ATTRIBUUT.TagString = "MATNUMMER_FLEXFIX" And ATTRIBUUT.TextString <> " " Then bb = ATTRIBUUT.TextString
                                             If ATTRIBUUT.TagString = "FLEXFIX_RETOUR" And ATTRIBUUT.TextString <> " " Then cc = ATTRIBUUT.TextString
                                             If ATTRIBUUT.TagString = "FLEXFIX_AANVOER" And ATTRIBUUT.TextString <> " " Then dd = ATTRIBUUT.TextString
                                             If ATTRIBUUT.TagString = "AANTAL_SLINGERS_FLEXFIX" And ATTRIBUUT.TextString <> " " Then ee = ATTRIBUUT.TextString
                                             If ATTRIBUUT.TagString = "BREEDTE_FLEXFIX" And ATTRIBUUT.TextString <> " " Then ff = ATTRIBUUT.TextString
                                             If ATTRIBUUT.TagString = "ROLLENGTE" And ATTRIBUUT.TextString <> " " Then gg = ATTRIBUUT.TextString
                                             If ATTRIBUUT.TagString = "GROEPTEKST" And ATTRIBUUT.TextString <> " " Then hh = ATTRIBUUT.TextString
                                             If ATTRIBUUT.TagString = "HOHAFSTAND" And ATTRIBUUT.TextString <> " " Then ii = ATTRIBUUT.TextString
                                             If ATTRIBUUT.TagString = "SL_RETOUR" And ATTRIBUUT.TextString <> " " Then jj = ATTRIBUUT.TextString
                                             If ATTRIBUUT.TagString = "SL_AANVOER" And ATTRIBUUT.TextString <> " " Then kk = ATTRIBUUT.TextString
                                        Next J
                                   End If
                      
                                   Next x
                        End If
                                    
                    Next i
                End If
            End If
        End If
                    If aa <> "" And bb <> "" And cc <> "" And dd <> "" And ee <> "" And ff <> "" And gg <> "" And hh <> "" _
                    And ii <> "" And jj <> "" And kk <> "" Then
                    
                    ll = aa & "+" & bb & "+" & cc & "+" & dd & "+" & ee & "+" & ff & "+" & gg & "+" & hh & "+" & ii & "+" & jj & "+" & kk
                    If ll <> "" Then frmflexfixexport.ListBox1.AddItem (ll)
                    ll = "": aa = "":  bb = "": cc = "": dd = "": ee = "": ff = "": gg = "": hh = "": ii = "": jj = "": kk = ""
                    End If
                    
          
         
    Next element

Call ffxs

End Sub
Sub ffxs()
Dim teknaam
Dim pad
Dim usernaam
Dim teknaam2
Const ForReading = 1, ForWriting = 2, ForAppending = 8
Dim fs, f
Dim s1 As AcadSelectionSet
Set fs = CreateObject("Scripting.FileSystemObject")
teknaam = ThisDrawing.GetVariable("dwgname")
teknaam2 = Split(teknaam, ".")
pad = ThisDrawing.GetVariable("dwgprefix")
usernaam = pad & teknaam2(0) & "-flexfix.xls"
Dim MyDate
MyDate = DateValue(Date)    ' Return a date.


Set f = fs.OpenTextFile(usernaam, ForWriting, -2)
    f.write "Unitnummer"
    f.write Chr(9)
    f.write "Matnummer_flexfix"
    f.write Chr(9)
    f.write "Flexfix_retour"
    f.write Chr(9)
    f.write "Flexfix_aanvoer"
    f.write Chr(9)
    f.write "Aantal_slingers_flexfix"
    f.write Chr(9)
    f.write "Breedte_flexfix"
    f.write Chr(9)
    f.write "Rollengte"
    f.write Chr(9)
    f.write "Groeptekst"
    f.write Chr(9)
    f.write "HOHafstand"
    f.write Chr(9)
    f.write "SL_retour"
    f.write Chr(9)
    f.write "SL_aanvoer"
    f.write Chr(10) + Chr(13)
    f.Close


teller = ListBox1.ListCount
    For i = 0 To teller - 1
       'Define the text object
        TextString = ListBox1.List(i)
        t2 = Split(TextString, "+")
        Set f = fs.OpenTextFile(usernaam, ForAppending, -2)
        f.write t2(0)
        f.write Chr(9)
        f.write t2(1)
        f.write Chr(9)
        f.write t2(2)
        f.write Chr(9)
        f.write t2(3)
        f.write Chr(9)
        f.write t2(4)
        f.write Chr(9)
        f.write t2(5)
        f.write Chr(9)
        f.write t2(6)
        f.write Chr(9)
        f.write t2(7)
        f.write Chr(9)
        f.write t2(8)
        f.write Chr(9)
        f.write t2(9)
        f.write Chr(9)
        f.write t2(10)
        f.write Chr(9)
        f.write Chr(13)
        f.Close
    Next i
Unload Me
End Sub

Attribute VB_Name = "frmlayerprojekt"
Attribute VB_Base = "0{10B820E2-A2E8-4CE7-B607-82B56F44DB85}{2297D4C7-4A4F-475E-9143-D3E2180FC80A}"
Attribute VB_GlobalNameSpace = False
Attribute VB_Creatable = False
Attribute VB_PredeclaredId = True
Attribute VB_Exposed = False
Attribute VB_TemplateDerived = False
Attribute VB_Customizable = False
Private Sub UserForm_Click()
'Call Checklayer.Checklayer  'module kijkt of er lege layers zijn

ListBox1.Clear
ListBox2.Clear
Update
On Error Resume Next
  
 Dim cirkel As Object
 Dim element As Object
 Dim Lengte As Double
 Dim laagobj As Object
 
 Dim minaantal As Integer
 Dim maxaantal As Integer
 Dim i As Integer
 i = 0
 minaantal = 0
 maxaantal = ThisDrawing.Layers.Count
 For Each laagobj In ThisDrawing.Layers
 i = i + 1
 ProgressBar1.Min = minaantal
 ProgressBar1.Max = maxaantal
 ProgressBar1.Value = i
 
      mystr = Left(laagobj.Name, 5)
      If mystr = "GROEP" Then mystr = "groep"
      If Not mystr = "groep" Then
      GoTo wand
      Else
        For Each element In ThisDrawing.ModelSpace
          If element.layer = laagobj.Name Then
                'BEREKENEN TOTALE LENGTE
                If element.EntityName = "AcDbLine" Then Lengte = Lengte + element.Length
                If element.EntityName = "AcDbArc" Then Lengte = Lengte + element.ArcLength
             End If 'elementlayer
             Next element
            
              For Each cirkel In ThisDrawing.ModelSpace
                If cirkel.layer = laagobj.Name Then
                If cirkel.EntityName = "AcDbCircle" Then
                Z = Z + 1
                wvaanwezig = " (WV)"
                zlengte = Z * 100 '(ComboBox1.Text * 100)) + 100
                End If
                End If
                Next cirkel
                
                
                
                
wand:
        If mystr = "WAND_" Then mystr = "wand_"
        If mystr = "wand_" Then
             For Each element In ThisDrawing.ModelSpace
             If element.layer = laagobj.Name Then
                'BEREKENEN TOTALE LENGTE
                If element.EntityName = "AcDbLine" Then Lengte = Lengte + element.Length
                If element.EntityName = "AcDbArc" Then Lengte = Lengte + element.ArcLength
                         
             End If 'elementlayer
             Next element
             
                For Each cirkel In ThisDrawing.ModelSpace
                If cirkel.layer = laagobj.Name Then
                If cirkel.EntityName = "AcDbCircle" Then
                Z = Z + 1
                wvaanwezig = " (WV)"
                End If
                End If
                Next cirkel
                zlengte = (Z * (ComboBox1.Text * 100)) + 100
                End If '2e mystr
                
    Lengte = (Lengte * TextBox19) + zlengte
    'Lengte = Lengte + zlengte
    Lengte = (Lengte / 100) + Val(TextBox27)
    Lengte = Round(Lengte, 2)
    totalrollen = totalrollen + Lengte
    
    'nieuwe tekeningen
''''    If frmLayerlijst.CheckBox3.Value = False Then
''''   'WTH-ZD-leiding
''''    If Lengte >= 162.5 And Lengte < 250 And OptionButton1.Value = True Then
''''    q250 = q250 + 1
''''    E = "--> wordt een rol van 250 meter"
''''    End If
''''    If Lengte >= 122.5 And Lengte < 162.5 And OptionButton1.Value = True Then
''''    q165 = q165 + 1
''''    E = "--> wordt een rol van 165 meter"
''''    End If
''''    If Lengte >= 102.5 And Lengte < 122.5 And OptionButton1.Value = True Then
''''    q125 = q125 + 1
''''    E = "--> wordt een rol van 125 meter"
''''    End If
''''    If Lengte >= 87.5 And Lengte < 102.5 And OptionButton1.Value = True Then
''''    q105 = q105 + 1
''''    E = "--> wordt een rol van 105 meter"
''''    End If
''''    If Lengte >= 72.5 And Lengte < 87.5 And OptionButton1.Value = True Then
''''    q90 = q90 + 1
''''    E = "--> wordt een rol van 90 meter"
''''    End If
''''    If Lengte >= 60.5 And Lengte < 72.5 And OptionButton1.Value = True Then
''''    q75 = q75 + 1
''''    E = "--> wordt een rol van 75 meter"
''''    End If
''''    If Lengte >= 47.5 And Lengte < 60.5 And OptionButton1.Value = True Then
''''    q63 = q63 + 1
''''    E = "--> wordt een rol van 63 meter"
''''    End If
''''    If Lengte >= 37.5 And Lengte < 47.5 And OptionButton1.Value = True Then
''''    q50 = q50 + 1
''''    E = "--> wordt een rol van 50 meter"
''''    End If
''''    If Lengte >= 10 And Lengte < 37.5 And OptionButton1.Value = True Then
''''    q40 = q40 + 1
''''    E = "--> wordt een rol van 40 meter"
''''    End If
    
    
'''''    'PE-RT-leiding
'''''    If Lengte >= 87.5 And Lengte < 120 And OptionButton2.Value = True Then
'''''    qpe120 = qpe120 + 1
'''''    E = "--> wordt een rol van 120 meter"
'''''    End If
'''''    If Lengte >= 120 And OptionButton2.Value = True And CheckBox5.Value = True Then
'''''    qpe120 = qpe120 + 1
'''''    E = "--> wordt een rol van 120 meter"
'''''    End If
'''''    If Lengte >= 57.5 And Lengte < 87.5 And OptionButton2.Value = True Then
'''''    qpe90 = qpe90 + 1
'''''    E = "--> wordt een rol van 90 meter"
'''''    End If
'''''    If Lengte >= 10 And Lengte < 57.5 And OptionButton2.Value = True Then
'''''    qpe60 = qpe60 + 1
'''''    E = "--> wordt een rol van 60 meter"
'''''    End If
'''''    End If 'nieuwe tekeningen
'''''
'''''  'oude tekeningen
''''''    If frmLayerlijst.CheckBox3.Value = True Then
''''''   'WTH-ZD-leiding
''''''    If Lengte >= 163.6 And Lengte < 250 And OptionButton1.Value = True Then
''''''    q250 = q250 + 1
''''''    E = "--> wordt een rol van 250 meter"
''''''    End If
''''''    If Lengte >= 123.6 And Lengte < 163.6 And OptionButton1.Value = True Then
''''''    q165 = q165 + 1
''''''    E = "--> wordt een rol van 165 meter"
''''''    End If
''''''    If Lengte >= 103.6 And Lengte < 123.6 And OptionButton1.Value = True Then
''''''    q125 = q125 + 1
''''''    E = "--> wordt een rol van 125 meter"
''''''    End If
''''''    If Lengte >= 88.6 And Lengte < 103.6 And OptionButton1.Value = True Then
''''''    q105 = q105 + 1
''''''    E = "--> wordt een rol van 105 meter"
''''''    End If
''''''    If Lengte >= 73.6 And Lengte < 88.6 And OptionButton1.Value = True Then
''''''    q90 = q90 + 1
''''''    E = "--> wordt een rol van 90 meter"
''''''    End If
''''''    If Lengte >= 61.6 And Lengte < 73.6 And OptionButton1.Value = True Then
''''''    q75 = q75 + 1
''''''    E = "--> wordt een rol van 75 meter"
''''''    End If
''''''    If Lengte >= 48.6 And Lengte < 61.6 And OptionButton1.Value = True Then
''''''    q63 = q63 + 1
''''''    E = "--> wordt een rol van 63 meter"
''''''    End If
''''''    If Lengte >= 38.6 And Lengte < 48.6 And OptionButton1.Value = True Then
''''''    q50 = q50 + 1
''''''    E = "--> wordt een rol van 50 meter"
''''''    End If
''''''    If Lengte >= 10 And Lengte < 38.6 And OptionButton1.Value = True Then
''''''    q40 = q40 + 1
''''''    E = "--> wordt een rol van 40 meter"
''''''    End If
    
    
''''''    'PE-RT-leiding
''''''    If Lengte >= 88.6 And Lengte < 120 And OptionButton2.Value = True Then
''''''    qpe120 = qpe120 + 1
''''''    E = "--> wordt een rol van 120 meter"
''''''    End If
''''''    If Lengte >= 120 And OptionButton2.Value = True And CheckBox5.Value = True Then
''''''    qpe120 = qpe120 + 1
''''''    E = "--> wordt een rol van 120 meter"
''''''    End If
''''''    If Lengte >= 58.6 And Lengte < 88.6 And OptionButton2.Value = True Then
''''''    qpe90 = qpe90 + 1
''''''    E = "--> wordt een rol van 90 meter"
''''''    End If
''''''    If Lengte >= 10 And Lengte < 58.6 And OptionButton2.Value = True Then
''''''    qpe60 = qpe60 + 1
''''''    E = "--> wordt een rol van 60 meter"
''''''    End If
''''''    End If 'oude tekeningen
''''''
  
''''''''   'wth-zd
''''''''    If Lengte > 250 And OptionButton1.Value = True Then
''''''''    Label15 = " !!!..DE MAX. ROLLENGTE WORDT OVERSCHREDEN...!!!"
''''''''    Label15.BackColor = &HFFFF&
''''''''    'e = "--> ROL IS TE LANG.!!!"
''''''''    overschrijding1 = 1
''''''''    'frmLayerlijst.Height = 243
''''''''    End If
''''''''    'PE-RT
''''''''    If Lengte > 120 And OptionButton2.Value = True And CheckBox5.Value = False Then
''''''''    Label15 = " !!!..DE MAX. ROLLENGTE WORDT OVERSCHREDEN...!!!"
''''''''    Label15.BackColor = &HFFFF&
''''''''    'e = "--> ROL IS TE LANG.!!!"
''''''''    overschrijding1 = 1
''''''''    'frmLayerlijst.Height = 243
''''''''    End If
''''''''
''''''''
    If mystr = "groep" Then
    s = " = "
    Else
    s = "  = " ' HIERO
    End If
    
    If mystr = "wand_" Or mystr = "WAND_" Or mystr = "groep" Or mystr = "GROEP" Then
    If Lengte < 10 Or Lengte > 120 And OptionButton2.Value = True And CheckBox5.Value = False Or Lengte > 250 And OptionButton1.Value = True Then
    d = "LET OP!! " & laagobj.Name & s & Lengte & " meter."
    ListBox2.AddItem (d)
    overschrijding2 = 1
    Else
    d = laagobj.Name & s & Lengte & " meter"
    mylen = Len(d)
    ListBox1.AddItem (d)
    End If
    End If
    
'''''    If OptionButton1.Value = True Then
'''''    TextBox2 = q250
'''''    TextBox3 = q165
'''''    TextBox4 = q125
'''''    TextBox5 = q105
'''''    TextBox6 = q90
'''''    TextBox7 = q75
'''''    TextBox8 = q63
'''''    TextBox10 = q50
'''''    TextBox11 = q40
'''''
'''''
'''''    If TextBox2 = "" Then TextBox2 = "0"
'''''    If TextBox3 = "" Then TextBox3 = "0"
'''''    If TextBox4 = "" Then TextBox4 = "0"
'''''    If TextBox5 = "" Then TextBox5 = "0"
'''''    If TextBox6 = "" Then TextBox6 = "0"
'''''    If TextBox7 = "" Then TextBox7 = "0"
'''''    If TextBox8 = "" Then TextBox8 = "0"
'''''    If TextBox10 = "" Then TextBox10 = "0"
'''''    If TextBox11 = "" Then TextBox11 = "0"
'''''
'''''
'''''
'''''    totaal2 = q250 + q165 + q125 + q105 + q90 + q75 + q63 + q50 + q40
'''''    End If
    
''''''    If OptionButton2.Value = True Then
''''''    TextBox2 = qpe120
''''''    TextBox3 = qpe90
''''''    TextBox4 = qpe60
''''''    TextBox5.Visible = False
''''''    TextBox6.Visible = False
''''''    TextBox7.Visible = False
''''''    TextBox8.Visible = False
''''''    TextBox10.Visible = False
''''''    TextBox11.Visible = False
''''''
''''''
''''''    If TextBox2 = "" Then TextBox2 = "0"
''''''    If TextBox3 = "" Then TextBox3 = "0"
''''''    If TextBox4 = "" Then TextBox4 = "0"
''''''    If TextBox21 = "" Then TextBox21 = "0"
''''''    If TextBox22 = "" Then TextBox22 = "0"
''''''    If TextBox23 = "" Then TextBox23 = "0"
''''''    If TextBox24 = "" Then TextBox24 = "0"
''''''    Label1.Caption = "120 meter"
''''''    Label3.Caption = "90 meter"
''''''    Label5.Caption = "60 meter"
''''''    Label7.Caption = Clear
''''''    Label8.Caption = Clear
''''''    Label10.Caption = Clear
''''''    Label13.Caption = Clear
''''''    Label21.Caption = Clear
''''''    Label22.Caption = Clear
''''''
''''''    totaal2 = qpe120 + qpe90 + qpe60
''''''    End If
    Lengte = 0 'Lengte leeggooien voordat de volgende groep wordt gemeten
    zlengte = 0
    Z = 0
    wvaanwezig = ""
  End If  'end if  mystr
 Next laagobj
 ProgressBar1.Value = minaantal
 Update
 
''''''  Label16 = totaal2
''''''  Label17 = " Totaal: " & totaal2 & " groep(en)"
'''''' If q250 = 0 And q165 = 0 And q125 = 0 And q105 = 0 And q90 = 0 And q75 = 0 _
'''''' And q63 = 0 And q50 = 0 And q40 = 0 And qpe120 = 0 And qpe90 = 0 And qpe60 = 0 Then
'''''' Cmdprint.Enabled = False
'''''' frmLayerlijst.Height = 346
'''''' Label15.Caption = " !!!...GEEN GROEPLAYERS AANWEZIG...!!!"
'''''' Label15.BackColor = &HFFFF&
'''''' Else
'''''' frmlayerprojekt.Width = 364 ''''''''''''''''''''''''''''''''''''''''''HIER
'''''' Cmdprint.Enabled = True
'''''' End If
'''''' If overschrijding1 = 1 Then frmLayerlijst.Height = 263 '243
'''''' If overschrijding2 = 1 Then frmLayerlijst.Height = 346 '290
'''''' If CheckBox5.Value = False Then
'''''' Label24.Visible = True
'''''' TextBox12.Visible = True
'''''' Else
'''''' Label24.Visible = False
'''''' TextBox12.Visible = False
'''''' End If
'''''' If OptionButton2.Value = True Then
'''''' CheckBox5.Visible = True
'''''' Else
'''''' CheckBox5.Visible = False
'''''' End If
''''''
   'lijst rangschikken
  Dim Veld(0 To 500)
  Dim textstring2 As String
  
    For i = 0 To ListBox1.ListCount - 1
    textstring2 = ListBox1.List(i)
    Veld(i) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next i
  ListBox1.Clear
 
  For x = 0 To UBound(Veld)
  If Veld(x) <> "" Then ListBox1.AddItem Veld(x)
  Next x
 TextBox12 = totalrollen
 TextBox20 = TextBox12
 TextBox26 = TextBox12
 If OptionButton2.Value = True Then CheckBox5.Enabled = False
 

End Sub

Attribute VB_Name = "frmopschoon"
Attribute VB_Base = "0{C9FE7E55-6B03-49FC-9BFE-BF7B55D3FA93}{B72211C9-515A-479B-972B-D9C76ACF55F4}"
Attribute VB_GlobalNameSpace = False
Attribute VB_Creatable = False
Attribute VB_PredeclaredId = True
Attribute VB_Exposed = False
Attribute VB_TemplateDerived = False
Attribute VB_Customizable = False
Private Sub cmdgo_Click()
'''    Dim drawing As AcadDocument
'''    For Each drawing In ThisDrawing.Application.Documents
'''    drawing.Activate
On Error Resume Next
ThisDrawing.SendCommand "audit" & vbCr & "y" & vbCr
        
    Dim objBlock As AcadBlock
    Dim objEntity As AcadEntity
    Dim objLayer As AcadLayer
    
''''      Dim mypos
''''
''''      For Each objBlock In ThisDrawing.Blocks
''''        For Each objEntity In objBlock
''''          mypos = InStr(1, objEntity, "STRAMIEN")
''''          objEntity.layer = "STRAMIEN"
''''          objEntity.color = acByLayer
''''          objEntity.Lineweight = acLnWtByLwDefault
''''        Next objEntity
''''      Next objBlock
         
Dim olddata As String
olddata = ThisDrawing.GetVariable("clayer")
ThisDrawing.SendCommand "-layer" & vbCr & "M" & vbCr & "BOUWKUNDIG" & vbCr & vbCr
ThisDrawing.SendCommand "-layer" & vbCr & "M" & vbCr & "3" & vbCr & vbCr
ThisDrawing.SendCommand "-layer" & vbCr & "Set" & vbCr & olddata & vbCr & vbCr
Update




  
      'alles naar layer bouwkundig
      Dim object3
        For Each object3 In ThisDrawing.ModelSpace
           object3.layer = "bouwkundig"
        Next
       
       
'set all object colors to bylayer
      For Each objBlock In ThisDrawing.Blocks
        For Each objEntity In objBlock
          objEntity.layer = "bouwkundig"
          objEntity.color = acByLayer
          objEntity.Lineweight = acLnWtByLwDefault
        Next objEntity
      Next objBlock
      
      ThisDrawing.SendCommand "burst" & vbCr & "all" & vbCr & vbCr
      
      
Dim layer
Dim entHandle As String
    Dim entry As AcadEntity
    For Each entry In ThisDrawing.ModelSpace
        entHandle = entry.ObjectName
        entry.Highlight (True)
        'MsgBox "The handle of this object is " & entHandle, vbInformation, "Handle Example"
        entry.Highlight (False)
        If entHandle = "AcDbDimension" Then entry.Delete
        If entHandle = "AcDbHatch" Then entry.Delete
        If entHandle = "AcDbSolid" Then entry.Delete
        If entHandle = "AcDbRotatedDimension" Then entry.Delete
        If entHandle = "AcDbAlignedDimension" Then entry.Delete
        If entHandle = "AcDbAngularDimension" Then entry.Delete
        
        If entHandle = "AcDbText" Then
            entry.layer = "3"
            entry.color = acByLayer
            If InStr(1, entry.TextString, "merk", vbBinaryCompare) Then entry.Delete
            If InStr(1, entry.TextString, "MERK", vbBinaryCompare) Then entry.Delete
        End If
        If entHandle = "AcDbMText" Then
    
            If InStr(1, entry.TextString, "merk", vbBinaryCompare) Then entry.Delete
            If InStr(1, entry.TextString, "MERK", vbBinaryCompare) Then entry.Delete
            If UCase(entry.TextString) = "K." Then entry.Delete
            If UCase(entry.TextString) = "MV" Then entry.Delete
            If UCase(entry.TextString) = "HWA" Then entry.Delete
            If UCase(entry.TextString) = "H.W.A." Then entry.Delete
            If UCase(entry.TextString) = "WINDVERBAND" Then entry.Delete
            entry.layer = "3"
            entry.color = acByLayer
        End If
        If entHandle = "AcDbImage" Then entry.Delete
        Update
    Next



ThisDrawing.PurgeAll
ThisDrawing.SendCommand "wthlayer" & vbCr
ThisDrawing.Save

'''    Next drawing

End Sub

Attribute VB_Name = "frmpdf"
Attribute VB_Base = "0{2A8CA517-3536-44C2-8830-B642715DAD18}{57DB91A2-38B4-4FC4-8E5B-3D5C17994739}"
Attribute VB_GlobalNameSpace = False
Attribute VB_Creatable = False
Attribute VB_PredeclaredId = True
Attribute VB_Exposed = False
Attribute VB_TemplateDerived = False
Attribute VB_Customizable = False
Private Sub CommandButton1_Click()
frmpdf.Hide
Dim a As String
Dim b As String
a = frmpdf.TextBox1
b = frmpdf.TextBox2
'MsgBox a
'MsgBox b
ThisDrawing.SendCommand "scale" & vbCr & "All" & vbCr & vbCr & "0.0" & vbCr & "R" & vbCr & a & vbCr & b & vbCr

ZoomAll
Unload Me
End Sub

Attribute VB_Name = "frmvervangen"
Attribute VB_Base = "0{789FB50E-4231-4075-8AB2-A7E49252FDE8}{8ED3E9C2-BCB7-4396-B958-3D701D4EE42B}"
Attribute VB_GlobalNameSpace = False
Attribute VB_Creatable = False
Attribute VB_PredeclaredId = True
Attribute VB_Exposed = False
Attribute VB_TemplateDerived = False
Attribute VB_Customizable = False
Option Explicit

'— Late-bind the AutoCAD application so you don't need a specific reference —
Private mappAcad As Object
Private mstrPath As String

#If VBA7 Then
  Private Declare PtrSafe Function FindWindow Lib "user32" Alias "FindWindowA" ( _
      ByVal lpClassName As String, _
      ByVal lpWindowName As String _
  ) As LongPtr

  Private Declare PtrSafe Function DrawMenuBar Lib "user32" ( _
      ByVal hWnd As LongPtr _
  ) As Long

  Private Declare PtrSafe Function GetMenuItemCount Lib "user32" ( _
      ByVal hMenu As LongPtr _
  ) As Long

  Private Declare PtrSafe Function GetSystemMenu Lib "user32" ( _
      ByVal hWnd As LongPtr, _
      ByVal bRevert As Long _
  ) As LongPtr

  Private Declare PtrSafe Function RemoveMenu Lib "user32" ( _
      ByVal hMenu As LongPtr, _
      ByVal nPosition As Long, _
      ByVal wFlags As Long _
  ) As Long
#Else
  Private Declare Function FindWindow Lib "user32" Alias "FindWindowA" ( _
      ByVal lpClassName As String, _
      ByVal lpWindowName As String _
  ) As Long

  Private Declare Function DrawMenuBar Lib "user32" ( _
      ByVal hWnd As Long _
  ) As Long

  Private Declare Function GetMenuItemCount Lib "user32" ( _
      ByVal hMenu As Long _
  ) As Long

  Private Declare Function GetSystemMenu Lib "user32" ( _
      ByVal hWnd As Long, _
      ByVal bRevert As Long _
  ) As Long

  Private Declare Function RemoveMenu Lib "user32" ( _
      ByVal hMenu As Long, _
      ByVal nPosition As Long, _
      ByVal wFlags As Long _
  ) As Long
#End If

Private Const MF_BYPOSITION = &H400
Private Const MF_REMOVE = &H1000
Private Sub CommandButton3_Click()
    Dim acadApp     As Object
    Dim doc         As Object
    Dim fdlCol      As Object
    Dim fdl         As Object
    Dim info        As String

    ' 1) Get the running AutoCAD (or fail)
    On Error Resume Next
    Set acadApp = GetObject(, "AutoCAD.Application")
    If acadApp Is Nothing Then
        MsgBox "Could not find a running instance of AutoCAD.", vbExclamation
        Exit Sub
    End If
    On Error GoTo 0

    ' 2) Open the drawing and zoom all
    Set doc = acadApp.Documents.Open("C:\acad2002\p08-01072.dwg")
    acadApp.ZoomAll

    ' 3) Late-bind the FileDependencies property
    On Error Resume Next
    Set fdlCol = CallByName(doc, "FileDependencies", VbGet)
    On Error GoTo 0

    If fdlCol Is Nothing Then
        MsgBox "FileDependencies is not supported in this AutoCAD version.", vbInformation
        Exit Sub
    End If

    ' Show how many entries there are
    MsgBox "The number of entries in the File Dependency List is " & _
           CallByName(fdlCol, "Count", VbGet) & "."

    ' 4) Loop and display each dependency
    For Each fdl In fdlCol
        info = ""
        info = info & "Affects graphics?: " & vbTab & CallByName(fdl, "AffectsGraphics", VbGet) & vbCrLf
        info = info & "Feature:         " & vbTab & CallByName(fdl, "Feature", VbGet) & vbCrLf
        info = info & "FileName:        " & vbTab & CallByName(fdl, "FileName", VbGet) & vbCrLf
        info = info & "FileSize:        " & vbTab & CallByName(fdl, "FileSize", VbGet) & vbCrLf
        info = info & "Fingerprint GUID:" & vbTab & CallByName(fdl, "FingerprintGuid", VbGet) & vbCrLf
        info = info & "FoundPath:       " & vbTab & CallByName(fdl, "FoundPath", VbGet) & vbCrLf
        info = info & "FullFileName:    " & vbTab & CallByName(fdl, "FullFileName", VbGet) & vbCrLf
        info = info & "Index:           " & vbTab & CallByName(fdl, "Index", VbGet) & vbCrLf
        info = info & "Modified?:       " & vbTab & CallByName(fdl, "IsModified", VbGet) & vbCrLf
        info = info & "ReferenceCount:  " & vbTab & CallByName(fdl, "ReferenceCount", VbGet) & vbCrLf
        info = info & "Timestamp:       " & vbTab & CallByName(fdl, "TimeStamp", VbGet) & vbCrLf
        info = info & "Version GUID:    " & vbTab & CallByName(fdl, "VersionGuid", VbGet)

        MsgBox info, vbInformation, "Dependency #" & CallByName(fdl, "Index", VbGet)
    Next
End Sub




Private Sub OptionButton1_Click()
  ComboBox1.Enabled = True
  ComboBox1.ListIndex = 0
End Sub

Private Sub OptionButton2_Click()
   ComboBox1.Enabled = True
  ComboBox1.ListIndex = 8
End Sub

Private Sub OptionButton3_Click()
   ComboBox1.Enabled = True
  ComboBox1.ListIndex = 0
End Sub

Private Sub OptionButton4_Click()
   ComboBox1.Enabled = True
  ComboBox1.ListIndex = 0
End Sub

Private Sub OptionButton5_Click()
   ComboBox1.Enabled = True
  ComboBox1.ListIndex = 0
End Sub

Private Sub OptionButton6_Click()
   ComboBox1.Enabled = True
   ComboBox1.ListIndex = 0
End Sub

''''
''''Sub ERASEBLOK()
''''Dim layerelement As Object
''''For Each layerelement In ThisDrawing.ModelSpace
''''  If layerelement.layer = "MONTAGEBLOK" Then layerelement.Erase
''''Update
''''Next layerelement
''''End Sub

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
  'create acadapplication object
  'Set mappAcad = GetObject(Class:="AutoCAD.Application")
  On Error Resume Next
    Set mappAcad = GetObject(Class:="AutoCAD.Application")
    If mappAcad Is Nothing Then
        MsgBox "Could not get AutoCAD.Application"
        Unload Me
        Exit Sub
    End If
    On Error GoTo 0
  
 ' now populate your combo-box exactly as before…
    With Me.ComboBox1
      .AddItem "0"
      .AddItem "WIJZIGING1"
      .AddItem "WIJZIGING2"
      .AddItem "WIJZIGING3"
      .AddItem "WIJZIGING4"
      .AddItem "WIJZIGING5"
      .AddItem "WIJZIGING6"
      .AddItem "WIJZIGING7"
      .AddItem "REVISIE"
      .ListIndex = 0
    End With
End Sub
Private Sub CommandButton1_Click()
lstDrawings.Clear  'reset button
ListBox1.Clear
OptionButton1.Value = False
OptionButton2.Value = False
OptionButton3.Value = False
OptionButton4.Value = False
OptionButton5.Value = False
OptionButton6.Value = False
ComboBox1.ListIndex = 0
End Sub
Private Sub UserForm_Terminate()
  'clean up
  Set mappAcad = Nothing

End Sub
Private Sub cmdClose_Click()

  'close this form
  Call Unload(Me)

End Sub

Private Sub cmdSelect_Click()
    Dim cd          As Object
    Dim strFileNames As String
    Dim varFiles    As Variant
    Dim i           As Long
    
    ' Late-bind the VB6 CommonDialog control
    On Error Resume Next
    Set cd = CreateObject("MSComDlg.CommonDialog")
    If cd Is Nothing Then
        MsgBox "MSComDlg32.ocx not available. Please register the Common Dialog control.", _
               vbExclamation
        Exit Sub
    End If
    On Error GoTo 0
    
    ' Configure and show the multi-select Open dialog
    With cd
        .Filter = "AutoCAD Drawings (*.dwg)|*.dwg"
        .FilterIndex = 1
        .MaxFileSize = 6000
        ' &H200 = OFN_ALLOWMULTISELECT, &H80000 = OFN_EXPLORER
        .Flags = &H200 Or &H80000
        .InitDir = mstrPath               ' remember last folder if you like
        .ShowOpen
        strFileNames = .FileName
    End With
    
    ' Nothing picked? bail out.
    If Len(strFileNames) = 0 Then Exit Sub
    
    ' Split the result on vbNullChar ? first element is folder, the rest are file names
    varFiles = Split(strFileNames, vbNullChar)
    
    ' Clear your two listboxes and fill them again
    Me.lstDrawings.Clear
    Me.ListBox1.Clear                  ' if you used a second ListBox for the path
    
    For i = 1 To UBound(varFiles)
        Me.lstDrawings.AddItem varFiles(i)
        Me.ListBox1.AddItem varFiles(0) & "\"     ' show the path next to each file
    Next i
    
    ' Update your TextBox1 with how many you picked
    Me.TextBox1 = Me.lstDrawings.ListCount
End Sub


Private Sub SplitFullFilename(ByVal strFullFilename As String, ByRef strPath As String, ByRef strFile As String)
  Dim intLen As Integer
  Dim intTmp As Integer
    
  'check given full filename length
  intLen = Len(strFullFilename)
  If intLen <> 0 Then
    'check whether full filename contains a path seperator
    If InStr(1, strFullFilename, "\", vbTextCompare) <> 0 Then
      'path seperator found, split path and filename
      For intTmp = intLen To 0 Step -1
        If Mid(strFullFilename, intTmp, 1) = "\" Then
          strFile = Right(strFullFilename, intLen - intTmp)
          strPath = Left(strFullFilename, intTmp) 'path waar de file staat
          ListBox1.AddItem (strPath)
          Exit For
        End If
      Next intTmp
    Else
      'return filename only
      strFile = strFullFilename  'filenaam+dwg
    End If
  End If

End Sub

Private Function FileExists(strFullFilename As String) As Boolean
  
  'check given filename string
  If Len(strFullFilename) <> 0 Then
    'check whether given filename exists
    If Len(Dir(strFullFilename, vbNormal)) <> 0 Then
      FileExists = True
    End If
  End If

End Function
Private Sub cmdStart_Click()
ThisDrawing.SendCommand "-layer" & vbCr & "U" & vbCr & "*" & vbCr & vbCr

'ThisDrawing.SendCommand "setvar" & vbCr & "acadlspasdoc" & vbCr & "0" & vbCr
  Dim intDrawing As Integer
  Dim intDrawings As Integer
  
  'check whether anyt valid files are selected
  If Len(mstrPath) <> 0 Then
    intDrawings = Me.lstDrawings.ListCount - 1
    If intDrawings >= 0 Then

      For intDrawing = 0 To intDrawings
      Call PrepareAsBackGround(ListBox1.List(intDrawing) & Me.lstDrawings.List(intDrawing))
      Next intDrawing
    End If
 
  End If


  Call Unload(Me)
'ThisDrawing.SendCommand "setvar" & vbCr & "acadlspasdoc" & vbCr & "1" & vbCr
End Sub
Sub ERASEBLOK()
 Dim element2
 For Each element2 In ThisDrawing.ModelSpace
      If element2.layer = "MONTAGEBLOK" Then
         element2.Erase
      End If
      Update
     Next element2
End Sub
Private Sub PrepareAsBackGround(strDrawingFullname As String)
    On Error GoTo ErrHandler
    
    '– local variables –
    Dim objDocument As Object                ' AcadDocument
    Dim element    As Object
    Dim attribs    As Variant
    Dim attrib     As Object
    Dim naamblok   As String
    Dim vINS As Doubl
    Dim i          As Long
    
    '– choose which logo/block to insert based on the radio buttons –
    If Me.OptionButton1.Value Then
        naamblok = "C:\ACAD2002\DWG\definitief2.dwg"
    ElseIf Me.OptionButton2.Value Then
        naamblok = "C:\ACAD2002\DWG\bl-revisie.dwg"
    ElseIf Me.OptionButton3.Value Then
        naamblok = "C:\ACAD2002\DWG\goedkeuring.dwg"
    ElseIf Me.OptionButton4.Value Then
        naamblok = "C:\ACAD2002\DWG\voorlopig.dwg"
    ElseIf Me.OptionButton5.Value Then
        naamblok = "C:\ACAD2002\DWG\uitvoering.dwg"
    ElseIf Me.OptionButton6.Value Then
        naamblok = "C:\ACAD2002\DWG\allesnaregelen.dwg"
    Else
        ' no option selected: nothing to do
        Exit Sub
    End If
    
    '– only proceed if the file actually exists –
    If Not FileExists(strDrawingFullname) Then Exit Sub
    
    '– open it as a background document –
    Set objDocument = mappAcad.Documents.Open(strDrawingFullname)
    
    '– update the date/block attributes in the new document –
    Call datum
    
    '– switch to layer GT in the current drawing –
    ThisDrawing.SendCommand "-layer" & vbCr & "Set" & vbCr & "GT" & vbCr & vbCr
    
    '– optionally erase existing montage-blocks –
    If Me.CheckBox1.Value Then ERASEBLOK
    
    '– purge all unused elements –
    ThisDrawing.SendCommand "-purge" & vbCr & "All" & vbCr & "*" & vbCr & "N" & vbCr
    
    '– remove any old logo-blocks and insert the new one at the same point –
    For Each element In objDocument.ModelSpace
        If element.ObjectName = "AcDbBlockReference" Then
            Select Case LCase(element.Name)
                Case "allesnaregelen", "definitief2", "definitief", _
                     "goedkeuring", "voorlopig", "bl-revisie", "uitvoering"
                     
                     ' capture the insertion point, erase the old block…
                     PE2 = element.InsertionPoint
                     element.Erase
                     
                     ' nudge up by 77 and insert new block
                     PE2(1) = PE2(1) + 77
                     objDocument.ModelSpace.InsertBlock PE2, naamblok, 1, 1, 1, 0
            End Select
        End If
    Next
    
    '– fill any “XXGROEPEN” blocks with default numeric attributes –
    For Each element In objDocument.ModelSpace
        If element.ObjectName = "AcDbBlockReference" Then
            If element.Name Like "##GROEPEN" Then
                attribs = element.GetAttributes
                For i = LBound(attribs) To UBound(attribs)
                    Set attrib = attribs(i)
                    Select Case attrib.TagString
                        Case "01", "02", "03", "04", "05", _
                             "06", "07", "08", "09", "10", _
                             "11", "12", "13", "14", "15", _
                             "16", "17", "18", "19", "20"
                             If attrib.TextString = "" Then
                                 attrib.TextString = CStr(Val(attrib.TagString))
                             End If
                    End Select
                Next
            End If
        End If
    Next
    
    '– save and close the background document –
    objDocument.Close SaveChanges:=True
    
    '– decrement your counter on the form –
    Me.frmvervangen.TextBox1 = Val(Me.frmvervangen.TextBox1) - 1
    If Val(Me.TextBox1) <> 0 Then
        Me.frmvervangen.Caption = _
          "Vervang Blok & Datum...nog " & Me.frmvervangen.TextBox1 & " tekening(en)."
    End If

Cleanup:
    Set objDocument = Nothing
    Exit Sub

ErrHandler:
    MsgBox "Error " & Err.Number & ": " & Err.Description, vbCritical
    Resume Cleanup
End Sub

Sub datum()
lognaam = ThisDrawing.GetVariable("loginname")
lognaam = UCase(lognaam)
If lognaam = "JMASI" Then lognaam = "JM"
If lognaam = "GERARD" Then lognaam = "GCH"
If lognaam = "ILONA" Then lognaam = "IK"
If lognaam = "BJORN" Then lognaam = "BC"
If lognaam = "DENNIS" Then lognaam = "DvdW"
If lognaam = "ZILVERSCHOONJ" Then lognaam = "JZ"
If lognaam = "BGOUW" Then lognaam = "BG"
If lognaam = "OYILM" Then lognaam = "OY"
If lognaam = "SNABI" Then lognaam = "SN"
If lognaam = "DLALI" Then lognaam = "DL"
If lognaam = "GLUII" Then lognaam = "GL"
If lognaam = "DWILS" Then lognaam = "DW"
If lognaam = "JPRINS" Then lognaam = "JP"
datumacad1 = ThisDrawing.GetVariable("cdate")
datumacad = Left(datumacad1, 8)

dag = Right(datumacad, 2)
maand = Left(datumacad, 6)
maand2 = Right(maand, 2)
jaar = Left(datumacad, 4)

kdate = dag & "-" & maand2 & "-" & jaar & "|" & lognaam

If ComboBox1 <> "0" Then
 wyz = ComboBox1

    Dim element As Object
    For Each element In ThisDrawing.ModelSpace
          If element.ObjectName = "AcDbBlockReference" Then
          If element.Name = "Kaderlogo" Then
          Set SYMBOOL = element
            If SYMBOOL.HasAttributes Then
            ATTRIBUTEN = SYMBOOL.GetAttributes
            For i = LBound(ATTRIBUTEN) To UBound(ATTRIBUTEN)
            Set ATTRIBUUT = ATTRIBUTEN(i)
                 If ATTRIBUUT.TagString = ComboBox1 Then ATTRIBUUT.TextString = kdate
            Next i
    
            End If
          End If
          End If
      Next element
End If
End Sub
Private Sub CommandButton2_Click()
Dim controle1
Dim controle2
Dim controle3
Dim controle4

frmvervangen.Hide
Dim pe1(0 To 2) As Double
Dim PE2(0 To 2) As Double
Dim pe6(0 To 2) As Double
Dim insp
Dim pe3 As String
Dim pe4 As String

Dim element As Object
For Each element In ThisDrawing.ModelSpace
      If element.ObjectName = "AcDbBlockReference" Then
          controle1 = InStr(1, element.Name, "h0.kl.1", vbTextCompare)
          controle2 = InStr(1, element.Name, "h1.kl.1", vbTextCompare)
          controle3 = InStr(1, element.Name, "h2.kl.1", vbTextCompare)
          controle4 = InStr(1, element.Name, "h3.kl.1", vbTextCompare)
           
          
          If controle1 <> 0 Or controle2 <> 0 Or controle3 <> 0 Or controle4 <> 0 Then
            insp = element.InsertionPoint
          pe1(0) = insp(0) + 7000
          pe1(1) = insp(1) + 10000
          pe1(2) = 0
          
          PE2(0) = insp(0) - 7000
          PE2(1) = insp(1) - 10000
          PE2(2) = 0
          
          pe6(0) = insp(0) + 2000
          pe6(1) = insp(1) - 9800
          pe6(2) = 0
          
          
          'MsgBox pe2
          
          pe3 = pe1(0) & "," & pe1(1)
          pe4 = PE2(0) & "," & PE2(1)
          'MsgBox pe3
          dwgnm = ThisDrawing.GetVariable("dwgname")
          Dim textObj As AcadText
          Set textObj = ThisDrawing.ModelSpace.AddText(dwgnm, pe6, 100)

          'ThisDrawing.SendCommand "text" & vbCr & pe4 & vbCr & "100" & vbCr & "90" & vbCr & dwgnm & vbCr
          ThisDrawing.SendCommand "-plot" & vbCr & "Y" & vbCr & "Model" & vbCr & "\\FSERVER2\P39 L2100TN" & vbCr & "A4" & vbCr & "M" & vbCr & "P" & vbCr & "N" & vbCr & "W" & vbCr & pe3 & vbCr & pe4 & vbCr & "F" & vbCr & "0,0" & vbCr & "Y" & vbCr & "wth.ctb" & vbCr & "Y" & vbCr & "N" & vbCr & "N" & vbCr & "Y" & vbCr & "Y" & vbCr
         
          
          
                                                                                                                                                                                                                                          

''          Set blockRefObj = ThisDrawing.ModelSpace.InsertBlock(insp, naamblok, 1, 1, 1, 0)
          End If
        
        End If
     Next element

End Sub

Attribute VB_Name = "frmverwijder"
Attribute VB_Base = "0{2C6EBBA6-8615-45C3-A203-3B18A6946467}{98E231D7-2620-4A65-A728-E574D216D6B0}"
Attribute VB_GlobalNameSpace = False
Attribute VB_Creatable = False
Attribute VB_PredeclaredId = True
Attribute VB_Exposed = False
Attribute VB_TemplateDerived = False
Attribute VB_Customizable = False
Private Sub CommandButton1_Click()
Dim layer
On Error Resume Next

Dim entHandle As String
    Dim entry As AcadEntity
    For Each entry In ThisDrawing.ModelSpace
        entHandle = entry.ObjectName
        'entry.Highlight (True)
  
        
        If entHandle = "AcDbText" Then
            If InStr(1, entry.TextString, TextBox1, vbBinaryCompare) Then entry.Delete
            If InStr(1, entry.TextString, UCase(TextBox1), vbBinaryCompare) Then entry.Delete
        End If
        
        If entHandle = "AcDbMText" Then
            If InStr(1, entry.TextString, TextBox1, vbBinaryCompare) Then entry.Delete
            If InStr(1, entry.TextString, UCase(TextBox1), vbBinaryCompare) Then entry.Delete
        End If
        
        Update

    Next
    
TextBox1 = Clear
TextBox1.SetFocus
End Sub

Private Sub CommandButton2_Click()
Unload Me
End Sub

'''''''''Private Sub CommandButton3_Click()
'''''''''
'''''''''frmverwijder.Hide
'''''''''
'''''''''Dim sset As AcadSelectionSet
'''''''''Set sset = ThisDrawing.SelectionSets.Add("SS3")
'''''''''sset.SelectOnScreen
'''''''''
'''''''''Dim ent As Object
'''''''''For Each ent In sset
'''''''''   If ent.ObjectName = "AcDbBlockreference" Then
'''''''''        b = ent.Object.Name
'''''''''      ListBox1.AddItem (b)
'''''''''   End If
'''''''''  ent.Update
'''''''''
'''''''''Next ent
'''''''''sset.Delete
'''''''''
'''''''''frmverwijder.Show
'''''''''
'''''''''End Sub

Private Sub CommandButton4_Click()
Dim layer
Dim entHandle As String
    Dim entry As AcadEntity
    For Each entry In ThisDrawing.ModelSpace
        entHandle = entry.ObjectName
        entry.Highlight (True)
        'MsgBox "The handle of this object is " & entHandle, vbInformation, "Handle Example"
        entry.Highlight (False)
        If entHandle = "AcDbBlockReference" Then ListBox1.AddItem (entry.Name)
        Update
    Next

End Sub

Private Sub CommandButton5_Click()

Dim layer
Dim entHandle As String
    Dim entry As AcadEntity
    For Each entry In ThisDrawing.ModelSpace
        entHandle = entry.ObjectName
        
        If entHandle = "AcDbText" Then
            
            If InStr(1, entry.TextString, "Keuken", vbBinaryCompare) Then entry.TextString = "Kitchen"
        End If
        
        If entHandle = "AcDbMText" Then
            If InStr(1, entry.TextString, "H.O.H. ", vbBinaryCompare) Then entry.TextString = " c.t.c. "
           
        End If
        
        Update
    Next

End Sub
