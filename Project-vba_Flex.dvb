Attribute VB_Name = "Module1"
Option Explicit
Sub Extraopties()
frmExtraopties.show
End Sub
Sub LegrichtingFF()
frmLegrichtingFF.show
End Sub
Sub Flexfixafstand()
frmFlexfixafstand.show
End Sub

Attribute VB_Name = "frmExtraopties"
Attribute VB_Base = "0{C872C40E-35AF-415F-A161-1A2F7F13CEDB}{A0303987-DD02-4293-8327-FBD9E607884E}"
Attribute VB_GlobalNameSpace = False
Attribute VB_Creatable = False
Attribute VB_PredeclaredId = True
Attribute VB_Exposed = False
Attribute VB_TemplateDerived = False
Attribute VB_Customizable = False
'23-2-2005 Extra Opties
'4-7-2005 wijziging
'M.Bosch en G.C.Haak

#If VBA7 Then
    Private Declare PtrSafe Function FindWindow Lib "user32" Alias "FindWindowA" _
    (ByVal lpClassName As String, ByVal lpWindowName As String) As LongPtr

    Private Declare PtrSafe Function DrawMenuBar Lib "user32" _
    (ByVal hWnd As LongPtr) As Long

    Private Declare PtrSafe Function GetMenuItemCount Lib "user32" _
    (ByVal hMenu As LongPtr) As Long

    Private Declare PtrSafe Function GetSystemMenu Lib "user32" _
    (ByVal hWnd As LongPtr, ByVal bRevert As Long) As LongPtr

    Private Declare PtrSafe Function RemoveMenu Lib "user32" _
    (ByVal hMenu As LongPtr, ByVal nPosition As Long, ByVal wFlags As Long) As Long
#Else
    Private Declare Function FindWindow Lib "user32" Alias "FindWindowA" _
    (ByVal lpClassName As String, ByVal lpWindowName As String) As Long

    Private Declare Function DrawMenuBar Lib "user32" _
    (ByVal hWnd As Long) As Long

    Private Declare Function GetMenuItemCount Lib "user32" _
    (ByVal hMenu As Long) As Long

    Private Declare Function GetSystemMenu Lib "user32" _
    (ByVal hWnd As Long, ByVal bRevert As Long) As Long

    Private Declare Function RemoveMenu Lib "user32" _
    (ByVal hMenu As Long, ByVal nPosition As Long, ByVal wFlags As Long) As Long
#End If

Private Const MF_BYPOSITION = &H400
Private Const MF_REMOVE = &H1000

Private Sub UserForm_Initialize()
#If VBA7 Then
    Dim lngHwnd As LongPtr
    Dim lngMenu As LongPtr
#Else
    Dim lngHwnd As Long
    Dim lngMenu As Long
#End If
    Dim lngCnt As Long

    lngHwnd = FindWindow(vbNullString, Me.Caption)
    lngMenu = GetSystemMenu(lngHwnd, 0)

    If lngMenu Then
        lngCnt = GetMenuItemCount(lngMenu)
        RemoveMenu lngMenu, lngCnt - 1, MF_REMOVE Or MF_BYPOSITION
        DrawMenuBar lngHwnd
    End If

    frmExtraopties.TextBox2.Value = 1
    frmExtraopties.TextBox3.SetFocus
End Sub

Private Sub CommandButton1_Click()
    On Error Resume Next
    Dim z1 As Double
    Dim z2 As Double
    Dim bb As Double
    Dim I As Long
    Dim cc As String
    Dim C As String
    Dim rr As Long
    Dim col As AcadAcCmColor
    Dim layColor As AcadAcCmColor
    Dim newLayer As AcadLayer

    z1 = Val(frmExtraopties.TextBox2)
    z2 = Val(frmExtraopties.TextBox3)

    If z2 < z1 Then
        MsgBox "De laatste waarde moet groter zijn dan de 1e....!!!!", vbExclamation, "Let op"
        Exit Sub
    End If

    cc = frmExtraopties.TextBox1 & "_" & Format(z1, "00")
    bb = z1

    For I = z1 To z2
        C = frmExtraopties.TextBox1 & "_" & Format(I, "00")
        Set newLayer = ThisDrawing.Layers.Add(C)
        ThisDrawing.ActiveLayer = newLayer

        rr = ThisDrawing.ActiveLayer.TrueColor.ColorIndex

        If rr = 2 Or rr = 7 Then
            Set layColor = AcadApplication.GetInterfaceObject("AutoCAD.AcCmColor.16")
            layColor.SetRGB 255, 255, 0
            ThisDrawing.ActiveLayer.TrueColor = layColor
        End If
    Next I

    frmExtraopties.TextBox2 = bb
    Set newLayer = ThisDrawing.Layers.Add(cc)
    ThisDrawing.ActiveLayer = newLayer
    Unload Me
End Sub

Private Sub TextBox2_Change()
    Dim b As Double
    On Error Resume Next
    b = Val(frmExtraopties.TextBox2.Text)

    If Err.Number <> 0 Then
        frmExtraopties.TextBox2 = ""
        PlaatsButton.Enabled = False
        Exit Sub
    End If

    If b <= 0 Then
        frmExtraopties.TextBox2 = ""
        frmExtraopties.TextBox2.SetFocus
    End If
End Sub

Private Sub TextBox3_Change()
    Dim a As Double
    On Error Resume Next
    a = Val(frmExtraopties.TextBox3.Text)

    If Err.Number <> 0 Then
        frmExtraopties.TextBox3 = ""
        PlaatsButton.Enabled = False
        Exit Sub
    End If

    If a <= 0 Then
        frmExtraopties.TextBox3 = ""
        frmExtraopties.TextBox3.SetFocus
    End If
End Sub

Private Sub cmdAfsluiten_Click()
    Unload Me
End Sub

Attribute VB_Name = "frmFlexfixafstand"
Attribute VB_Base = "0{9D1B1325-87F4-410D-A8BA-440148499D7B}{DF5888ED-0246-4A6A-8D2C-468952A6B9FC}"
Attribute VB_GlobalNameSpace = False
Attribute VB_Creatable = False
Attribute VB_PredeclaredId = True
Attribute VB_Exposed = False
Attribute VB_TemplateDerived = False
Attribute VB_Customizable = False
'13-09-2005 Flexfixafstand
'M.Bosch en G.C.Haak

#If VBA7 Then
    Private Declare PtrSafe Function FindWindow Lib "user32" Alias "FindWindowA" _
    (ByVal lpClassName As String, ByVal lpWindowName As String) As LongPtr

    Private Declare PtrSafe Function DrawMenuBar Lib "user32" _
    (ByVal hWnd As LongPtr) As Long

    Private Declare PtrSafe Function GetMenuItemCount Lib "user32" _
    (ByVal hMenu As LongPtr) As Long

    Private Declare PtrSafe Function GetSystemMenu Lib "user32" _
    (ByVal hWnd As LongPtr, ByVal bRevert As Long) As LongPtr

    Private Declare PtrSafe Function RemoveMenu Lib "user32" _
    (ByVal hMenu As LongPtr, ByVal nPosition As Long, ByVal wFlags As Long) As Long
#Else
    Private Declare Function FindWindow Lib "user32" Alias "FindWindowA" _
    (ByVal lpClassName As String, ByVal lpWindowName As String) As Long

    Private Declare Function DrawMenuBar Lib "user32" _
    (ByVal hWnd As Long) As Long

    Private Declare Function GetMenuItemCount Lib "user32" _
    (ByVal hMenu As Long) As Long

    Private Declare Function GetSystemMenu Lib "user32" _
    (ByVal hWnd As Long, ByVal bRevert As Long) As Long

    Private Declare Function RemoveMenu Lib "user32" _
    (ByVal hMenu As Long, ByVal nPosition As Long, ByVal wFlags As Long) As Long
#End If

Private Const MF_BYPOSITION = &H400
Private Const MF_REMOVE = &H1000

Private Sub UserForm_Initialize()
#If VBA7 Then
    Dim lngHwnd As LongPtr
    Dim lngMenu As LongPtr
#Else
    Dim lngHwnd As Long
    Dim lngMenu As Long
#End If
    Dim lngCnt As Long

    lngHwnd = FindWindow(vbNullString, Me.Caption)
    lngMenu = GetSystemMenu(lngHwnd, 0)

    If lngMenu Then
        lngCnt = GetMenuItemCount(lngMenu)
        RemoveMenu lngMenu, lngCnt - 1, MF_REMOVE Or MF_BYPOSITION
        DrawMenuBar lngHwnd
    End If
End Sub

Private Sub cmdAfsluiten_Click()
    Unload Me
    If OptionButton1.Value = True Then ThisDrawing.SetVariable "filletrad", 10
    If OptionButton2.Value = True Then ThisDrawing.SetVariable "filletrad", 12.5
    If OptionButton3.Value = True Then ThisDrawing.SetVariable "filletrad", 15
    If OptionButton4.Value = True Then ThisDrawing.SetVariable "filletrad", 20
    If OptionButton5.Value = True Then ThisDrawing.SetVariable "filletrad", 25
    If OptionButton6.Value = True Then ThisDrawing.SetVariable "filletrad", 30
End Sub

Attribute VB_Name = "frmLegrichtingFF"
Attribute VB_Base = "0{68811B4C-788E-429B-B19D-5756D66DC450}{B16CD4D0-8384-495C-AD5E-928730D48393}"
Attribute VB_GlobalNameSpace = False
Attribute VB_Creatable = False
Attribute VB_PredeclaredId = True
Attribute VB_Exposed = False
Attribute VB_TemplateDerived = False
Attribute VB_Customizable = False
'09-09-2005 Legrichting bepalen
'M.Bosch en G.C.Haak

#If VBA7 Then
    Private Declare PtrSafe Function FindWindow Lib "user32" Alias "FindWindowA" (ByVal lpClassName As String, ByVal lpWindowName As String) As LongPtr
    Private Declare PtrSafe Function DrawMenuBar Lib "user32" (ByVal hWnd As LongPtr) As Long
    Private Declare PtrSafe Function GetMenuItemCount Lib "user32" (ByVal hMenu As LongPtr) As Long
    Private Declare PtrSafe Function GetSystemMenu Lib "user32" (ByVal hWnd As LongPtr, ByVal bRevert As Long) As LongPtr
    Private Declare PtrSafe Function RemoveMenu Lib "user32" (ByVal hMenu As LongPtr, ByVal nPosition As Long, ByVal wFlags As Long) As Long
#Else
    Private Declare Function FindWindow Lib "user32" Alias "FindWindowA" (ByVal lpClassName As String, ByVal lpWindowName As String) As Long
    Private Declare Function DrawMenuBar Lib "user32" (ByVal hWnd As Long) As Long
    Private Declare Function GetMenuItemCount Lib "user32" (ByVal hMenu As Long) As Long
    Private Declare Function GetSystemMenu Lib "user32" (ByVal hWnd As Long, ByVal bRevert As Long) As Long
    Private Declare Function RemoveMenu Lib "user32" (ByVal hMenu As Long, ByVal nPosition As Long, ByVal wFlags As Long) As Long
#End If

Private Const MF_BYPOSITION = &H400
Private Const MF_REMOVE = &H1000

Private Sub UserForm_Initialize()
#If VBA7 Then
    Dim lngHwnd As LongPtr
    Dim lngMenu As LongPtr
#Else
    Dim lngHwnd As Long
    Dim lngMenu As Long
#End If
Dim lngCnt As Long
Dim box1 As Variant

lngHwnd = FindWindow(vbNullString, Me.Caption)
lngMenu = GetSystemMenu(lngHwnd, 0)

If lngMenu Then
    lngCnt = GetMenuItemCount(lngMenu)
    RemoveMenu lngMenu, lngCnt - 1, MF_REMOVE Or MF_BYPOSITION
    DrawMenuBar lngHwnd
End If

box1 = ThisDrawing.GetVariable("angdir")

If box1 = 0 Then OptionButton1.Value = True
If box1 = 1 Then OptionButton2.Value = True
End Sub

Private Sub cmdAfsluiten_Click()
If OptionButton1.Value = True Then ThisDrawing.SetVariable "angdir", 0
If OptionButton2.Value = True Then ThisDrawing.SetVariable "angdir", 1
Unload Me
End Sub
