Attribute VB_Name = "Check_Kaderlogo"
'checken of er meerdere kaderlogo's in de tekening staan
Sub Check_Kaderlogo()

Dim element As Object
For Each element In ThisDrawing.ModelSpace
      If element.ObjectName = "AcDbBlockReference" Then
         If element.Name = "Kaderlogo" Or element.Name = "KaderlogoEngels" Or element.Name = "logotgh" Then a = a + 1
      End If
Next element
      
      
If a > 1 Then

For Each element In ThisDrawing.ModelSpace
      If element.ObjectName = "AcDbBlockReference" Then
       If element.Name = "Kaderlogo" Or element.Name = "KaderlogoEngels" Or element.Name = "logotgh" Then
       Set symbool = element
        If symbool.HasAttributes Then
        attributen = symbool.GetAttributes
        For I = LBound(attributen) To UBound(attributen)
        Set attribuut = attributen(I)
        If attribuut.TagString = "OPDRACHTGEVER" And attribuut.textstring = "" Then element.Erase
        Next I
       End If
     End If
   End If
  Next element

End If



Dim pe2(0 To 2) As Double
Dim element2
Dim insp

For Each element2 In ThisDrawing.ModelSpace
      If element2.ObjectName = "AcDbBlockReference" Then
         If element2.Name = "ba3" Or element2.Name = "ba2" Or element2.Name = "ba1" _
         Or element2.Name = "ba0" Or element2.Name = "ba0+" Then
          insp = element2.InsertionPoint

          pe2(0) = insp(0)
          pe2(1) = insp(1)
          pe2(2) = 0
          If pe2(0) <> 0 Or pe2(1) <> 0 Then
          MsgBox "Je kader staat niet goed...!!!", vbCritical
          element2.Erase
          Exit Sub
          End If
          'MsgBox pe2(0) & " - " & pe2(1) & " - " & pe2(2) & " - "

          End If

      End If
Next element2

End Sub

Attribute VB_Name = "Checklayer1"
Sub Checklayer1()
On Error Resume Next

'Dim varData As Variant
'varData = ThisDrawing.GetVariable("users5")

'If varData <> "check" Then
'als groepslayer leeg is dan verwijderen
'wordt de 1e keer automatisch uitgevoerd
Dim layerObj As Object
For Each layerObj In ThisDrawing.Layers
  mystr = Left(layerObj.Name, 4)
  If mystr = "groep" Or mystr = "GROEP" Or mystr = "wand" Or mystr = "WAND" Then
  If layerObj.Length = 0 Then layerObj.Delete
 End If 'mystr
Next layerObj
Update
'End If

'ThisDrawing.SetVariable "users5", "check"
End Sub

Attribute VB_Name = "Checklayer2"
Sub Checklayer2()
On Error Resume Next

'als groepslayer leeg is dan verwijderen
'uitgevoerd na knop indrukken
Dim layerObj As Object
For Each layerObj In ThisDrawing.Layers
  mystr = Left(layerObj.Name, 5)
   If mystr = "groep" Or mystr = "GROEP" Or mystr = "wand" Or mystr = "WAND" Then
    If layerObj.Length = 0 Then layerObj.Delete
   End If 'mystr
Next layerObj
Update

'frmGroeptekst.Hide
ThisDrawing.SendCommand "-purge" & vbCr & "all" & vbCr & "*" & vbCr & "N" & vbCr
ThisDrawing.SendCommand "wthlayer" & vbCr
'frmGroeptekst.Show
End Sub

Attribute VB_Name = "Checklayer3"
Sub Checklayer3(a)

'kijken of de groepslayer al gebruikt is.
'a = 0
Dim element As Object
Dim layerObj As AcadLayer

optel = frmGroeptekst.TextBox10
  If optel > 0 And optel < 10 Then groeponder10 = "0"
unittel = frmGroeptekst.TextBox9
    
  If frmGroeptekst.CheckBox3.Value = False Then
    If unittel > 0 And unittel < 10 Then unitonder10 = "0"
    groepsnummer = "groep " & unitonder10 & frmGroeptekst.TextBox9 & "." & groeponder10 & optel    'tekst samenvoegen
    End If
  If frmGroeptekst.CheckBox3.Value = True Then
    groepsnummer = "groep " & frmGroeptekst.TextBox9 & "." & groeponder10 & optel    'tekst samenvoegen
  End If
  
'groepsnummer = "groep " & frmGroeptekst.TextBox9 & "." & groeponder10 & optel  'tekst samenvoegen

For Each layerObj In ThisDrawing.Layers
     If layerObj.Name = groepsnummer Then
       '  fixlayer = "groep " & unitonder10 & frmGroeptekst.TextBox9 & "." & groeponder10 & optel & "h"
       '  layerObj.Name = fixlayer
       ' MsgBox "Layernaam bestaat al.!!! --> Eerst de layernaam hernummeren voordat je verder gaat.!!!", vbExclamation
      a = 1
      frmGroeptekst.TextBox12 = frmGroeptekst.TextBox9
      'frmGroeptekst.TextBox9 = Clear
      'frmGroeptekst.TextBox10 = Clear
      'frmGroeptekst.TextBox12.SetFocus
      'Exit Sub
     End If
Next 'layerobj

End Sub

Attribute VB_Name = "Checklayer4"
Sub Checklayer4()
On Error Resume Next

'als groepslayer leeg is dan verwijderen i.v.m. dubbele layernamen 1.01 en 1.01h bijvoorbeeld
'uitgevoerd na knop indrukken
Dim layerObj As Object
For Each layerObj In ThisDrawing.Layers
  mystr = Left(layerObj.Name, 5)
   If mystr = "groep" Or mystr = "GROEP" Or mystr = "wand" Or mystr = "WAND" Then
    If layerObj.Length = 0 Then layerObj.Delete
   End If 'mystr
Next layerObj
Update

End Sub

Attribute VB_Name = "Checktekst"
Sub Checktekst(a)

'kijken of de groeptekst al gebruikt is.
a = 0
Dim element As Object
Dim layerObj As AcadLayer

optel = frmGroeptekst.TextBox10
  If optel > 0 And optel < 10 Then groeponder10 = "0"
unittel = frmGroeptekst.TextBox9
    
  If frmGroeptekst.CheckBox3.Value = False Then
    If unittel > 0 And unittel < 10 Then unitonder10 = "0"
    groepsnummer = "groep " & unitonder10 & frmGroeptekst.TextBox9 & "." & groeponder10 & optel    'tekst samenvoegen
    End If
  If frmGroeptekst.CheckBox3.Value = True Then
    groepsnummer = "groep " & frmGroeptekst.TextBox9 & "." & groeponder10 & optel    'tekst samenvoegen
  End If
  
'groepsnummer = "groep " & frmGroeptekst.TextBox9 & "." & groeponder10 & optel  'tekst samenvoegen

For Each element In ThisDrawing.ModelSpace
      If element.ObjectName = "AcDbBlockReference" Then
        If element.Name = "groeptekstbloknew" Or element.Name = "GROEPTEKSTBLOKNEW" Then
        Set symbool = element
         If symbool.HasAttributes Then
           attributen = symbool.GetAttributes
           For I = LBound(attributen) To UBound(attributen)
           Set attribuut = attributen(I)
            If attribuut.TagString = "GROEPTEKST" Then sjektekst = attribuut.textstring
             If groepsnummer = sjektekst Then
               MsgBox "Groeptekst al gebruikt", vbExclamation
               a = 1
               frmGroeptekst.TextBox9 = Clear
               frmGroeptekst.TextBox10 = Clear
               frmGroeptekst.TextBox9.SetFocus
               Exit Sub
            End If
           Next I
        End If
      End If
    End If
  Next element
End Sub

Attribute VB_Name = "M_Meten"
Sub Meten(RetObj, Pbase, eg)
    Dim element As Object
    Dim Lengte As Double
    Dim Lengte3 As Double
    Dim totallengte As String       'EBR, DEC 2002
    'Dim eg As Double         'EBR, DEC 2002: declareren van variabelen
    Dim optel As Integer            'EBR, DEC 2002: declareren van variabelen
    Dim unittel As Integer            'EBR, DEC 2002: declareren van variabelen
    Dim groepsnummer As String      'EBR, DEC 2002: declareren van variabelen
    check_layernaam = Left(RetObj.Layer, 4)
      
    frmGroeptekst.Hide
    ThisDrawing.SendCommand "-layer" & vbCr & "U" & vbCr & "GT" & vbCr & vbCr
    Update
    
    'On Error Resume Next           'EBR, DEC 2002 uitgezet !
    
   '----------------------------------------------------------------
    ' BEPALEN MIDDELPUNT OF CENTERPUNT BEPALEN
    '----------------------------------------------------------------
    
    If RetObj.EntityName = "AcDbLine" Then
        Dim PBEGIN As Variant
        Dim Peind As Variant
        Dim Pmid(0 To 2) As Double
        'Dim Pmid As Variant
        
        PBEGIN = RetObj.startPoint
        Peind = RetObj.endPoint
        
        Pmid(0) = (PBEGIN(0) + Peind(0)) / 2
        Pmid(1) = (PBEGIN(1) + Peind(1)) / 2
        Pmid(2) = 0
        'Dim PUNT As AcadPoint
        'Set PUNT = ThisDrawing.ModelSpace.AddPoint(Pmid)
        'PUNT.Color = acGreen
    Else
        
        Pmid(0) = Pbase(0)
        Pmid(1) = Pbase(1)
        Pmid(2) = 0
        
    End If
    
    '----------------------------------------------------------------
    ' MAKEN SELECTIESET
    '----------------------------------------------------------------
    
        
    Dim ssetObj As AcadSelectionSet
    Dim mode As Integer
    Dim pointsArray(0 To 14) As Double
    
    'NIEUW
    'On Error Resume Next
    Set ssetObj = ThisDrawing.SelectionSets.Add("TEST_SSET")
    If Err Then ThisDrawing.SelectionSets.Item("TEST_SSET").Delete
    mode = acSelectionSetCrossingPolygon
    
    Dim tel As Integer
    Dim sHandle As String
    Dim LijnGevonden As Boolean
    Dim ArcGevonden As Boolean
    
    
Opnieuw:
    
    tel = tel + 1
    
    pointsArray(0) = Pmid(0) - tel: pointsArray(1) = Pmid(1) - tel: pointsArray(2) = 0
    pointsArray(3) = Pmid(0) + tel: pointsArray(4) = Pmid(1) - tel: pointsArray(5) = 0
    pointsArray(6) = Pmid(0) + tel: pointsArray(7) = Pmid(1) + tel: pointsArray(8) = 0
    pointsArray(9) = Pmid(0) - tel: pointsArray(10) = Pmid(1) + tel: pointsArray(11) = 0
    pointsArray(12) = Pmid(0) - tel: pointsArray(13) = Pmid(1) - tel: pointsArray(14) = 0
    
    ssetObj.SelectByPolygon mode, pointsArray
   
    '----------------------------------------------------------------
    ' LEZEN SELECTIESET
    '----------------------------------------------------------------
    
    If tel > 120 Then
        ssetObj.Clear
        ssetObj.Delete
        MsgBox "Geen juiste HOH gevonden.!!" & (Chr(13) & Chr(10)) & "Ik zoom nu uit," & Chr(13) & "wijs daarna de groep weer aan.", vbInformation
        tel = 0
        ZoomPrevious
        GoTo Opnieuw
        'End
    End If

     If ssetObj.Count > 1 Then
        
            For Each element In ssetObj
            If RetObj.Handle <> element.Handle Then
                If element.Layer = RetObj.Layer Then
                        If element.EntityName = "AcDbLine" And RetObj.EntityName = "AcDbLine" Then
                            sHandle = element.Handle
                            LijnGevonden = True
                            Exit For
                        End If
                        If element.EntityName = "AcDbArc" And RetObj.EntityName = "AcDbArc" Then
                            sHandle = element.Handle
                            ArcGevonden = True
                            Exit For
                        End If
                End If
            End If
            Next element
            
            If LijnGevonden = False And ArcGevonden = False Then GoTo Opnieuw
    Else
            GoTo Opnieuw
    End If
    
    ssetObj.Clear
    ssetObj.Delete
    
    '----------------------------------------------------------------
    ' SNIJPUNT MET LIJN BEREKENEN EN BEPALEN HOH
    '----------------------------------------------------------------
    Dim HOH As Double
       
    If RetObj.EntityName = "AcDbLine" Then
    
            Dim LijnObj As AcadLine
            Dim Peind1(0 To 2) As Double
            
            Peind1(0) = Pmid(0) + 35
            Peind1(1) = Pmid(1)
            Peind1(2) = 0
            
        
            Set LijnObj = ThisDrawing.ModelSpace.AddLine(Pmid, Peind1)
            LijnObj.Rotate Pmid, RetObj.Angle + 1.57075
                          
            Dim Ps As Variant   'snijpunt
            Dim IntersectObject As Object
            Set IntersectObject = ThisDrawing.HandleToObject(sHandle)
            
            Ps = LijnObj.IntersectWith(IntersectObject, acExtendBoth)
            
            '-------------------------------------
            'NIEUW
            '-------------------------------------
            ' weergeven van alle snijpunten
            Dim I As Integer, j As Integer, k As Integer
            Dim str As String
            If VarType(Ps) <> vbEmpty Then
                For I = LBound(Ps) To UBound(Ps)
            'uitgezet GCH  MsgBox "x=" & Round(Ps(j), 0) & Chr(10) & Chr(13) & "y=" & Round(Ps(j + 1), 0) & Chr(10) & Chr(13) & "z=" & Round(Ps(j + 2), 0), , "Snijpunt"
                    I = I + 2
                    j = j + 3
                    'k = k + 1
                Next
            End If
            
            '-------------------------------------
            LijnObj.Erase
             Dim puntobj As Object
            'uitgezet GCH  Set puntobj = ThisDrawing.ModelSpace.AddPoint(Ps)
            'uitgezet GCH  Set puntobj = ThisDrawing.ModelSpace.AddPoint(Pmid)
            ' BEPALEN HOH
            HOH = 0
            HOH = Lengte2(Ps, Pmid)
            
            
            
    Else
            
            'Dim puntobj2 As Object
            'puntobj2 = acMagenta
     'Set puntobj2 = ThisDrawing.ModelSpace.AddPoint(Peind1)
            
    '----------------------------------------------------------------
    ' STRAAL BEPALEN EN BEPALEN HOH
    '----------------------------------------------------------------
        
        Dim GevondenArcObj As AcadArc
        Dim ArcRadius As Double
        
        Set GevondenArcObj = ThisDrawing.HandleToObject(sHandle)
        ArcRadius = GevondenArcObj.radius
        HOH = Abs(RetObj.radius - ArcRadius)
    End If

    '----------------------------------------------------------------
    ' AFBEELDEN HOH
    '----------------------------------------------------------------
   
    HOH = Format(HOH, "0.0")
    'MsgBox HOH
    'frmGroeptekst.TextBox8 = "HOH " & HOH
    
    'EBR, DEC 2002: TOT HIER WERKT HET NU GOED !!!
    'MsgBox "EBR: v.a. hier ging het fout."
    'Exit Sub
   
    '-------------------
    'METEN VAN DE GROEP
    '-------------------
    If Err <> 0 Then
        Err.Clear
        MsgBox "Geen element geselecteerd", vbCritical, "Let op."
    Else
        For Each element In ThisDrawing.ModelSpace
              If element.Layer = RetObj.Layer Then
                'BEREKENEN TOTALE LENGTE
                If element.EntityName = "AcDbLine" Then Lengte = Lengte + element.Length
                If element.EntityName = "AcDbArc" Then Lengte = Lengte + element.ArcLength
              End If
        Next element
    End If
             z = 0
             Dim cirkel As Object
             For Each cirkel In ThisDrawing.ModelSpace
                If cirkel.Layer = RetObj.Layer Then
                If cirkel.EntityName = "AcDbCircle" Then z = z + 1
                End If
                Next cirkel
                
       If frmGroeptekst.ToggleButton1.Value = False Then wandhoogte = 2.5
       If frmGroeptekst.ToggleButton1.Value = True Then wandhoogte = 2
       If frmGroeptekst.OptionButton5 = True Then wandhoogte = frmGroeptekst.TextBox13
                
                If z <> 0 Then zlengte = (z * (100 * wandhoogte)) + 100
    
    Lengte = Lengte + zlengte
    
   'LENGTE IN METERS
    Lengte = Lengte / 100
    Lengte = Round(Lengte, 1)
    Lengte = Lengte + Val(frmGroeptekst.TextBox28) '4-10-2006  restlengte voor als de verdeler beneden staat
    
    'MsgBox "Lengte=" & Lengte, , "Ebr: tot hier werkt het goed !"
    'EBR, DEC 2002: TOT HIER WERKT HET NU GOED !!!
    ' Exit Sub
    
    'WTH-ZD  nieuwe tekeningen
If frmGroeptekst.CheckBox3.Value = False Then
    If frmGroeptekst.OptionButton1.Value = True Then
        If Lengte >= 162.5 And Lengte < 247.5 Then Lengte3 = 250
        If Lengte >= 122.5 And Lengte < 162.5 Then Lengte3 = 165
        If Lengte >= 102.5 And Lengte < 122.5 Then Lengte3 = 125
        If Lengte >= 87.5 And Lengte < 102.5 Then Lengte3 = 105
        If Lengte >= 72.5 And Lengte < 87.5 Then Lengte3 = 90
        If Lengte >= 60.5 And Lengte < 72.5 Then Lengte3 = 75
        If Lengte >= 47.5 And Lengte < 60.5 Then Lengte3 = 63
        If Lengte >= 37.5 And Lengte < 47.5 Then Lengte3 = 50
        If Lengte >= 10 And Lengte < 37.5 Then Lengte3 = 40
           
       If frmGroeptekst.CheckBox4.Value = True Then Lengte3 = 125
       If Lengte > 247.4 Then MsgBox "Je rol is te lang..!!!!", vbExclamation, "Let op."
        
    End If
    
    'wth-zd-16*2,7 per 20-11-2007
        If frmGroeptekst.OptionButton9.Value = True Then
            If Lengte >= 87.5 And Lengte < 102.5 Then Lengte3 = 105
            If Lengte >= 72.5 And Lengte < 87.5 Then Lengte3 = 90
            If Lengte >= 60.5 And Lengte < 72.5 Then Lengte3 = 75
            If Lengte < 60.5 Then Lengte3 = 63
            If frmGroeptekst.CheckBox4.Value = True Then Lengte3 = 125
            If Lengte > 102.4 Then MsgBox "Je rol is te lang..!!!! [ max.105]", vbExclamation, "Let op."
        End If
    
    'PE-RT
    If frmGroeptekst.OptionButton2.Value = True Then
        If Lengte >= 87.5 And Lengte < 117.5 Then Lengte3 = 120
        If Lengte >= 57.5 And Lengte < 87.5 Then Lengte3 = 90
        If Lengte >= 10 And Lengte < 57.5 Then Lengte3 = 60
        If Lengte > 117.4 Then MsgBox "Je rol is te lang..!!!!", vbExclamation, "Let op."
    End If
    'Aluflex
    If frmGroeptekst.OptionButton6.Value = True Then
        If Lengte >= 97.5 And Lengte < 197.5 Then Lengte3 = 200
        If Lengte >= 47.5 And Lengte < 97.5 Then Lengte3 = 100
        If Lengte >= 10 And Lengte < 47.5 Then Lengte3 = 50
        If Lengte > 197.4 Then MsgBox "Je rol is te lang..!!!!", vbExclamation, "Let op."
    End If
End If
    
''''''''''''''''''''''oude tekeningen
'''''''''''''''''''''If frmGroeptekst.CheckBox3.Value = True Then
'''''''''''''''''''''    If frmGroeptekst.OptionButton1.Value = True Then
'''''''''''''''''''''        If Lengte >= 163.6 And Lengte < 250 Then Lengte3 = 250
'''''''''''''''''''''        If Lengte >= 123.6 And Lengte < 163.6 Then Lengte3 = 165
'''''''''''''''''''''        If Lengte >= 103.6 And Lengte < 123.6 Then Lengte3 = 125
'''''''''''''''''''''        If Lengte >= 88.6 And Lengte < 103.6 Then Lengte3 = 105
'''''''''''''''''''''        If Lengte >= 73.6 And Lengte < 88.6 Then Lengte3 = 90
'''''''''''''''''''''        If Lengte >= 61.6 And Lengte < 73.6 Then Lengte3 = 75
'''''''''''''''''''''        If Lengte >= 48.6 And Lengte < 61.6 Then Lengte3 = 63
'''''''''''''''''''''        If Lengte >= 38.6 And Lengte < 48.6 Then Lengte3 = 50
'''''''''''''''''''''        If Lengte >= 10 And Lengte < 38.6 Then Lengte3 = 40
'''''''''''''''''''''        If Lengte > 247.4 Then MsgBox "Je rol is te lang..!!!!", vbExclamation, "Let op."
'''''''''''''''''''''    End If
    'PE-RT
    
''''''''''''''''''''    If frmGroeptekst.OptionButton2.Value = True Then
''''''''''''''''''''        If Lengte >= 88.6 And Lengte < 118.6 Then Lengte3 = 120
''''''''''''''''''''        If Lengte >= 61.6 And Lengte < 88 Then Lengte3 = 90
''''''''''''''''''''        If Lengte >= 10 And Lengte < 61.6 Then Lengte3 = 60
''''''''''''''''''''        If Lengte > 118.5 Then
''''''''''''''''''''           MsgBox "Je rol is te lang..!!!!", vbExclamation, "Let op."
''''''''''''''''''''        Exit Sub
''''''''''''''''''''        End If
''''''''''''''''''''    End If
''''''''''''''''''''    'Aluflex
''''''''''''''''''''    If frmGroeptekst.OptionButton6.Value = True Then
''''''''''''''''''''        If Lengte >= 98.6 And Lengte < 197.5 Then Lengte3 = 200
''''''''''''''''''''        If Lengte >= 48.6 And Lengte < 98.6 Then Lengte3 = 100
''''''''''''''''''''        If Lengte >= 10 And Lengte < 48.6 Then Lengte3 = 50
''''''''''''''''''''        If Lengte > 197.4 Then MsgBox "Je rol is te lang..!!!!", vbExclamation, "Let op."
''''''''''''''''''''    End If
''''''''''''''''''''End If
    
    If frmGroeptekst.CheckBox1 = True Then Lengte3 = frmGroeptekst.TextBox14
    
    zz = frmGroeptekst.Label11.Caption
    'MsgBox zz & " | " & retobj.Layer
    If zz = RetObj.Layer Then
    optel = frmGroeptekst.TextBox10        'textbox10 uitlezen
    tvl = " "
    totallengte = " "
    Else
    'MsgBox "eg= " & eg
    If eg = 0 Then optel = frmGroeptekst.TextBox10 'uitlezen 1e keer
    If eg <> 0 Then optel = frmGroeptekst.TextBox10 + 1 '1 erbij optellen
    totallengte = Lengte3 & " meter"
    tvl = Lengte & " meter"
    End If
    
    If optel > 0 And optel < 10 Then groeponder10 = "0"
    
   
    unittel = frmGroeptekst.TextBox9
    

    If frmGroeptekst.CheckBox3.Value = False Then
           If unittel > 0 And unittel < 10 Then unitonder10 = "0"
           groepsnummer = "groep " & unitonder10 & frmGroeptekst.TextBox9 & "." & groeponder10 & optel 'tekst samenvoegen
    End If
    If frmGroeptekst.CheckBox3.Value = True Then
    groepsnummer = "groep " & unitonder10 & frmGroeptekst.TextBox9 & "." & groeponder10 & optel 'tekst samenvoegen
    End If
    
    zz = groepsnummer
    frmGroeptekst.Label11.Caption = zz
    
    eg = 1 'EERSTE GROEP
    frmGroeptekst.TextBox10 = optel
    'MsgBox optel
    
    'groepslengte op de commandregel
    zzz = groepsnummer & " = " & Lengte & " meter." & " [" & Val(frmGroeptekst.TextBox28) & "]"
    
    ThisDrawing.Utility.Prompt zzz
    ThisDrawing.SendCommand Chr(27)
    
       
    '-------------------------------------------------
    '  groeptekst plaatsen in de tekening
    '-------------------------------------------------
    Dim newLayer As AcadLayer
    
    
    Set newLayer = ThisDrawing.Layers.Add("GT")
    ThisDrawing.ActiveLayer = newLayer
    Update
        
    Dim hohafstand As String
    hohafstand = "H.O.H. " & HOH & " cm."
    If check_layernaam = "wand" Then hohafstand = "Wandverwarming"
    On Error Resume Next
    
    Dim Zoekpad As String
    Dim blockRefObj As Object       'EBR: var declareren
    
    ' wth
    Zoekpad = "C:\ACAD2002\DWG\groeptekstbloknew.dwg"
    
    ' ebr
    ' Zoekpad = "C:\temp\groeptekstbloknew.dwg"
    
    Set blockRefObj = ThisDrawing.ModelSpace.InsertBlock(Pbase, Zoekpad, 1, 1, 1, 0)
    
    'DOOR EBR DEC 2002:
    If Err Then
        Err.Clear
        MsgBox "symbool " & Zoekpad & " niet gevonden.", vbCritical, "Let op":
        End
    End If
    
'DOOR EBR DEC 2002: enkele aanpassingen

    Dim symbool As Object       'EBR altijd juist declareren
    Dim attributen As Variant   'EBR altijd juist declareren
    Dim attribuut As Object     'EBR altijd juist declareren
    If frmGroeptekst.OptionButton1 = True Then LW = "WTH-ZD 20*3,4 mm"
    If frmGroeptekst.OptionButton9 = True Then LW = "WTH-ZD 16*2,7 mm"
    If frmGroeptekst.OptionButton2 = True Then LW = frmGroeptekst.ComboBox4
    If frmGroeptekst.OptionButton6 = True Then LW = frmGroeptekst.ComboBox4
    
       If frmGroeptekst.OptionButton7 = True Then
         RL = "RM"
         Else
         RL = " "
      End If
    If frmGroeptekst.OptionButton8 = True Then
              groepsnummer = " "
              RL = "RZ"
    End If
    
    ' !!!!!!!!!!!!!!!!!!!!!!!!!!!!!!!!!!!!!!!!!!!!!!!!!!!!!!!!!!!!!!!!!!!!!!!
    For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                         Set attribuut = attributen(I)
                         If attribuut.TagString = "RINGLEIDING" And attribuut.textstring = "" Then attribuut.textstring = RL
                         If attribuut.TagString = "LEIDINGSOORT" And attribuut.textstring = "" Then attribuut.textstring = LW
                         If attribuut.TagString = "UNITNUMMER" And attribuut.textstring = "" Then attribuut.textstring = unitonder10 & frmGroeptekst.TextBox9
                         If attribuut.TagString = "GROEPTEKST" And attribuut.textstring = "" Then attribuut.textstring = groepsnummer
                         If attribuut.TagString = "HOHAFSTAND" And attribuut.textstring = "" Then attribuut.textstring = hohafstand
                         If attribuut.TagString = "TLVL" And attribuut.textstring = "" Then attribuut.textstring = tvl
                         If attribuut.TagString = "ROLLENGTE" And attribuut.textstring = "" Then attribuut.textstring = totallengte
                         If attribuut.TagString = "WERKLENGTE" And attribuut.textstring = "" Then attribuut.textstring = "nee"
                         If attribuut.TagString = "WANDHOOGTE" And check_layernaam = "groe" And attribuut.textstring = "" Then attribuut.textstring = " "
                         If attribuut.TagString = "WANDHOOGTE" And check_layernaam = "wand" And attribuut.textstring = "" Then attribuut.textstring = wandhoogte & " meter hoog"
                    Next I
                End If
            End If
        End If
    Next element
    
    Dim layerObj As AcadLayer
    For Each layerObj In ThisDrawing.Layers
         If layerObj.Name = RetObj.Layer Then layerObj.Name = groepsnummer
    Next
    
    
    End Sub
Public Function Lengte2(p1 As Variant, p2 As Variant) As Double

    'FUNCTIE VOOR HET BEREKENEN VAN DE AFSTAND TUSSEN TWEE PUNTEN
    
    Dim DX As Double
    Dim DY As Double
    
    DX = Abs(p2(0) - p1(0))
    DY = Abs(p2(1) - p1(1))

    Lengte2 = Sqr((DX ^ 2) + (DY ^ 2))
    'MsgBox lengte2
End Function

Attribute VB_Name = "M_Meten_Flexfix"
Sub Meten_Flexfix(RetObj, Pbase, eg)
    'Dim retobj As Object
    'Dim Pbase As Variant
    Dim element As Object
    Dim Lengte As Double
    Dim Lengte3 As Double
    Dim totallengte As String       'EBR, DEC 2002
    'Dim eg As Double         'EBR, DEC 2002: declareren van variabelen
    Dim optel As Integer            'EBR, DEC 2002: declareren van variabelen
    Dim unittel As Integer          'EBR, DEC 2002: declareren van variabelen
    Dim groepsnummer As String      'EBR, DEC 2002: declareren van variabelen
    check_layernaam = Left(RetObj.Layer, 4)
    'MsgBox check_layernaam
      
    frmGroeptekst.Hide
    'ThisDrawing.SendCommand "-layer" & vbCr & "U" & vbCr & "GT" & vbCr & vbCr
    Update
    
    'On Error Resume Next           'EBR, DEC 2002 uitgezet !
    
   '----------------------------------------------------------------
    ' BEPALEN MIDDELPUNT OF CENTERPUNT BEPALEN
    '----------------------------------------------------------------
    
    If RetObj.EntityName = "AcDbLine" Then
        Dim PBEGIN As Variant
        Dim Peind As Variant
        Dim Pmid(0 To 2) As Double
        'Dim Pmid As Variant
        
        PBEGIN = RetObj.startPoint
        Peind = RetObj.endPoint
        
        Pmid(0) = (PBEGIN(0) + Peind(0)) / 2
        Pmid(1) = (PBEGIN(1) + Peind(1)) / 2
        Pmid(2) = 0
        'Dim PUNT As AcadPoint
        'Set PUNT = ThisDrawing.ModelSpace.AddPoint(Pmid)
        'PUNT.Color = acGreen
    Else
        
        Pmid(0) = Pbase(0)
        Pmid(1) = Pbase(1)
        Pmid(2) = 0
        
    End If
    
    '----------------------------------------------------------------
    ' MAKEN SELECTIESET
    '----------------------------------------------------------------
    
        
    Dim ssetObj As AcadSelectionSet
    Dim mode As Integer
    Dim pointsArray(0 To 14) As Double
    
    'NIEUW
    'On Error Resume Next
    Set ssetObj = ThisDrawing.SelectionSets.Add("TEST_SSET")
    If Err Then ThisDrawing.SelectionSets.Item("TEST_SSET").Delete
    mode = acSelectionSetCrossingPolygon
    
    Dim tel As Integer
    Dim sHandle As String
    Dim LijnGevonden As Boolean
    Dim ArcGevonden As Boolean
    
    
Opnieuw:
    
    tel = tel + 1
    
    pointsArray(0) = Pmid(0) - tel: pointsArray(1) = Pmid(1) - tel: pointsArray(2) = 0
    pointsArray(3) = Pmid(0) + tel: pointsArray(4) = Pmid(1) - tel: pointsArray(5) = 0
    pointsArray(6) = Pmid(0) + tel: pointsArray(7) = Pmid(1) + tel: pointsArray(8) = 0
    pointsArray(9) = Pmid(0) - tel: pointsArray(10) = Pmid(1) + tel: pointsArray(11) = 0
    pointsArray(12) = Pmid(0) - tel: pointsArray(13) = Pmid(1) - tel: pointsArray(14) = 0
    
    ssetObj.SelectByPolygon mode, pointsArray
   
    '----------------------------------------------------------------
    ' LEZEN SELECTIESET
    '----------------------------------------------------------------
    
    If tel > 120 Then
        ssetObj.Clear
        ssetObj.Delete
        MsgBox "Geen juiste HOH gevonden.!!" & (Chr(13) & Chr(10)) & "Ik zoom nu uit," & Chr(13) & "wijs daarna de groep weer aan.", vbInformation
        tel = 0
        ZoomPrevious
        GoTo Opnieuw
        'End
    End If

     If ssetObj.Count > 1 Then
        
            For Each element In ssetObj
            If RetObj.Handle <> element.Handle Then
                If element.Layer = RetObj.Layer Then
                        If element.EntityName = "AcDbLine" And RetObj.EntityName = "AcDbLine" Then
                            sHandle = element.Handle
                            LijnGevonden = True
                            Exit For
                        End If
                        If element.EntityName = "AcDbArc" And RetObj.EntityName = "AcDbArc" Then
                            sHandle = element.Handle
                            ArcGevonden = True
                            Exit For
                        End If
                End If
            End If
            Next element
            
            If LijnGevonden = False And ArcGevonden = False Then GoTo Opnieuw
    Else
            GoTo Opnieuw
    End If
    
     lang = element.Length 't.b.v. flexfix

    
    ssetObj.Clear
    ssetObj.Delete
    
    '----------------------------------------------------------------
    ' SNIJPUNT MET LIJN BEREKENEN EN BEPALEN HOH
    '----------------------------------------------------------------
    Dim HOH As Double
       
    If RetObj.EntityName = "AcDbLine" Then
    
            Dim LijnObj As AcadLine
            Dim Peind1(0 To 2) As Double
            
            Peind1(0) = Pmid(0) + 35
            Peind1(1) = Pmid(1)
            Peind1(2) = 0
            
        
            Set LijnObj = ThisDrawing.ModelSpace.AddLine(Pmid, Peind1)
            LijnObj.Rotate Pmid, RetObj.Angle + 1.57075
                          
            Dim Ps As Variant   'snijpunt
            Dim IntersectObject As Object
            Set IntersectObject = ThisDrawing.HandleToObject(sHandle)
            
            Ps = LijnObj.IntersectWith(IntersectObject, acExtendBoth)
            
            '-------------------------------------
            'NIEUW
            '-------------------------------------
            ' weergeven van alle snijpunten
            Dim I As Integer, j As Integer, k As Integer
            Dim str As String
            If VarType(Ps) <> vbEmpty Then
                For I = LBound(Ps) To UBound(Ps)
            'uitgezet GCH  MsgBox "x=" & Round(Ps(j), 0) & Chr(10) & Chr(13) & "y=" & Round(Ps(j + 1), 0) & Chr(10) & Chr(13) & "z=" & Round(Ps(j + 2), 0), , "Snijpunt"
                    I = I + 2
                    j = j + 3
                    'k = k + 1
                Next
            End If
            
            '-------------------------------------
            LijnObj.Erase
             Dim puntobj As Object
            'uitgezet GCH  Set puntobj = ThisDrawing.ModelSpace.AddPoint(Ps)
            'uitgezet GCH  Set puntobj = ThisDrawing.ModelSpace.AddPoint(Pmid)
            ' BEPALEN HOH
            HOH = 0
            HOH = Lengte2(Ps, Pmid)
            
            
    Else
            
            'Dim puntobj2 As Object
            'puntobj2 = acMagenta
     'Set puntobj2 = ThisDrawing.ModelSpace.AddPoint(Peind1)
            
    '----------------------------------------------------------------
    ' STRAAL BEPALEN EN BEPALEN HOH
    '----------------------------------------------------------------
        
        Dim GevondenArcObj As AcadArc
        Dim ArcRadius As Double
        
        Set GevondenArcObj = ThisDrawing.HandleToObject(sHandle)
        ArcRadius = GevondenArcObj.radius
        HOH = Abs(RetObj.radius - ArcRadius)
    End If

    '----------------------------------------------------------------
    ' AFBEELDEN HOH
    '----------------------------------------------------------------
   
    HOH = Format(HOH, "0.0")
    'MsgBox HOH
    'frmGroeptekst.TextBox8 = "HOH " & HOH
    
    'EBR, DEC 2002: TOT HIER WERKT HET NU GOED !!!
    'MsgBox "EBR: v.a. hier ging het fout."
    'Exit Sub
   lang2 = lang + HOH  'FLEXFIX BREEDTE
   lang2 = Round(lang2, 0) 'FLEXFIX BREEDTE

    '-------------------
    'METEN VAN DE GROEP
    '-------------------
    If Err <> 0 Then
        Err.Clear
        MsgBox "Geen element geselecteerd", vbCritical, "Let op."
    Else
        For Each element In ThisDrawing.ModelSpace
             If element.Layer = RetObj.Layer Then
                'BEREKENEN TOTALE LENGTE
                If element.EntityName = "AcDbLine" Then Lengte = Lengte + element.Length
                     If element.EntityName = "AcDbArc" Then
                     Lengte = Lengte + element.ArcLength
                     arctel = arctel + 1
                     End If
              End If
             Next element
             
          faanvoer = RetObj.Layer & "_Flexfix_aanvoer"
          fretour = RetObj.Layer & "_Flexfix_retour"
          
          'als de layers hernoemd zijn en er tijdelijk een h achter de layer staat
          myaanvoer = Right(RetObj.Layer, 1)
          'myaanvoerlengte = Len(retobj.Layer)
          If myaanvoer = "h" Then
            myaanvoerleft = Split(RetObj.Layer, "_")
            faanvoer = myaanvoerleft(0) & "_Flexfix_aanvoerh"
            fretour = myaanvoerleft(0) & "_Flexfix_retourh"
            
            'myaanvoerlengte = myaanvoerlengte - 1
            'myaanvoerleft = Left(retobj.Layer, myaanvoerlengte)
            'faanvoer = myaanvoerleft & "_aanvoer"
            'fretour = myaanvoerleft & "_retour"
            End If
           'als de layers hernoemd zijn en er tijdelijk een h achter de layer staat
           
         'faanvoerh = retobj.Layer & "_Flexfix_aanvoerh"
   
         For Each elementaanvoer In ThisDrawing.ModelSpace
             If elementaanvoer.Layer = faanvoer Then
                'BEREKENEN TOTALE Lengteaanvoer
                If elementaanvoer.EntityName = "AcDbLine" Then lengteaanvoer = lengteaanvoer + elementaanvoer.Length
                     If elementaanvoer.EntityName = "AcDbArc" Then
                     lengteaanvoer = lengteaanvoer + elementaanvoer.ArcLength
                     End If
              End If
             Next elementaanvoer
             
           
           'fretourh = retobj.Layer & "_Flexfix_retourh"
          For Each elementretour In ThisDrawing.ModelSpace
             If elementretour.Layer = fretour Then
                'BEREKENEN TOTALE Lengteretour
                If elementretour.EntityName = "AcDbLine" Then lengteretour = lengteretour + elementretour.Length
                     If elementretour.EntityName = "AcDbArc" Then
                     lengteretour = lengteretour + elementretour.ArcLength
                     End If
              End If
             Next elementretour
        End If
    
    'LENGTE IN METERS
    reserve = 3
    reserve = reserve / 2
    
    If frmGroeptekst.CheckBox7 = True Then
      reserve = (Val(frmGroeptekst.TextBox24))
      reserve = reserve / 2
    End If
    'MsgBox reserve
    
    lengteaanvoer = Round((lengteaanvoer / 100), 1) + reserve
    lengteaanvoer = lengteaanvoer + (Val(frmGroeptekst.TextBox28) / 2)
    lengteretour = Round((lengteretour / 100), 1) + reserve
    lengteretour = lengteretour + (Val(frmGroeptekst.TextBox28) / 2)
    
    Lengte = Lengte / 100
    Lengte = Lengte + lengteaanvoer + lengteretour
    Lengte = Round(Lengte, 1)
    'Lengte = Lengte
    
    lang3 = (lang2 / 100)
    lang4 = lang3 * 2
    
    slingeraanvoer1 = lengteaanvoer / lang4 'lang2 = breedte flexfix
    slingeraanvoer2 = Fix(slingeraanvoer1 + 1)
    'MsgBox slingeraanvoer & "-" & lengteaanvoer & "-" & lang2
    slingerretour1 = lengteretour / lang4 'lang2 = breedte flexfix
    slingerretour2 = Fix(slingerretour1 + 1)
    
    '-------------------
    'EINDE METEN VAN DE GROEP
    '-------------------
    
    'MsgBox "Lengte=" & Lengte, , "Ebr: tot hier werkt het goed !"
    'EBR, DEC 2002: TOT HIER WERKT HET NU GOED !!!
    ' Exit Sub
      '---------------------------------
    '[meten flexfix aanvoer en retour]
    '---------------------------------
       
    zz = frmGroeptekst.Label11.Caption & "_Flexfix"
    
    If zz = RetObj.Layer Then
    optel = frmGroeptekst.TextBox10        'textbox10 uitlezen
    totallengte = " "
    ffoptie = 1
    Else
    'MsgBox "eg= " & eg
    If eg = 0 Then optel = frmGroeptekst.TextBox10 'uitlezen 1e keer
    If eg <> 0 Then optel = frmGroeptekst.TextBox10 + 1 '1 erbij optellen
    totallengte = Lengte & " meter"
    End If
    If optel > 0 And optel < 10 Then groeponder10 = "0"
    
    unittel = frmGroeptekst.TextBox9
       
    
       
       
    If frmGroeptekst.CheckBox3.Value = False Then
    If unittel > 0 And unittel < 10 Then unitonder10 = "0"
    groepsnummer = "groep " & unitonder10 & frmGroeptekst.TextBox9 & "." & groeponder10 & optel    'tekst samenvoegen
    End If
    If frmGroeptekst.CheckBox3.Value = True Then
    groepsnummer = "groep " & frmGroeptekst.TextBox9 & "." & groeponder10 & optel    'tekst samenvoegen
    End If
   
       
    zz = groepsnummer
    'frmGroeptekst.Label11.Caption = Clear
    frmGroeptekst.Label11.Caption = zz
    
    eg = 1 'EERSTE GROEP
    frmGroeptekst.TextBox10 = optel
    'MsgBox optel
    
    'groepslengte op de commandregel
    zzz = groepsnummer & " = " & Lengte & " meter." & " [" & Val(frmGroeptekst.TextBox28) & "]"
    ThisDrawing.Utility.Prompt zzz
    ThisDrawing.SendCommand Chr(27)
    
    
     If frmGroeptekst.CheckBox6.Value = True Then '--- flexfix matnummer
        unittel = frmGroeptekst.TextBox10
         If unittel > 0 And unittel < 10 Then
         unitonder11 = "0"
         mm = unitonder11 & frmGroeptekst.TextBox10 'tekst samenvoegen
         Else
         mm = frmGroeptekst.TextBox10 'tekst samenvoegen
         End If
     End If
       
    '-------------------------------------------------
    '  groeptekst plaatsen in de tekening
    '-------------------------------------------------
    Dim newLayer As AcadLayer
    
    
    Set newLayer = ThisDrawing.Layers.Add("GT")
    ThisDrawing.ActiveLayer = newLayer
    Update
        
    Dim hohafstand As String
    hohafstand = "H.O.H. " & HOH & " cm."
    If check_layernaam = "wand" Then hohafstand = "Wandverwarming"
    On Error Resume Next
    
    Dim Zoekpad As String
    Dim blockRefObj As Object       'EBR: var declareren
    
    ' wth
    Zoekpad = "C:\ACAD2002\DWG\groeptekstbloknew.dwg"
    
    Set blockRefObj = ThisDrawing.ModelSpace.InsertBlock(Pbase, Zoekpad, 1, 1, 1, 0)
    
    'DOOR EBR DEC 2002:
    If Err Then
        Err.Clear
        MsgBox "symbool " & Zoekpad & " niet gevonden.", vbCritical, "Let op":
        End
    End If
    
'DOOR EBR DEC 2002: enkele aanpassingen

    Dim symbool As Object       'EBR altijd juist declareren
    Dim attributen As Variant   'EBR altijd juist declareren
    Dim attribuut As Object     'EBR altijd juist declareren
    If frmGroeptekst.OptionButton1 = True Then LW = "WTH-ZD 20*3,4 mm"
    If frmGroeptekst.OptionButton9 = True Then LW = "WTH-ZD 16*2,7 mm"
    If frmGroeptekst.OptionButton2 = True Then LW = frmGroeptekst.ComboBox4
    If frmGroeptekst.OptionButton6 = True Then LW = frmGroeptekst.ComboBox4
   If frmGroeptekst.OptionButton7 = True Then
      RL = "RM"
      Else
      RL = " "
    End If
    If frmGroeptekst.OptionButton8 = True Then
              groepsnummer = " "
              RL = "RZ"
    End If
    
    arctel2 = (arctel / 2)
    arctel3 = Round(arctel2, 1)
    arctel3 = arctel3 / 2  '7-6

    lengtearc = Len(arctel3)
    If lengtearc > 2 Then arctel3 = arctel3 + 0.5
    arctel3 = Fix(arctel3)
        'MsgBox arctel3
   
    'If CheckBox6.Value = True Then FF = "ja"
'    If ffoptie = 1 Then
'        LANG2 = "-" 'breedte flexfix
'        arctel3 = "-" 'FLEXFIX AANTAL BOCHTEN
'        lengteaanvoer = "-"
'        lengteretour = "-"
'    End If
     
    
    
    
    For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                    Set attribuut = attributen(I)
                         If attribuut.TagString = "RINGLEIDING" And attribuut.textstring = "" Then attribuut.textstring = RL
                         If attribuut.TagString = "LEIDINGSOORT" And attribuut.textstring = "" Then attribuut.textstring = LW
                         If attribuut.TagString = "UNITNUMMER" And attribuut.textstring = "" Then attribuut.textstring = unitonder10 & frmGroeptekst.TextBox9
                         If attribuut.TagString = "GROEPTEKST" And attribuut.textstring = "" Then attribuut.textstring = groepsnummer
                         If attribuut.TagString = "HOHAFSTAND" And attribuut.textstring = "" Then attribuut.textstring = hohafstand
                         If attribuut.TagString = "ROLLENGTE" And attribuut.textstring = "" Then attribuut.textstring = " "
                         If attribuut.TagString = "TLVL" And attribuut.textstring = "" Then attribuut.textstring = totallengte
                         
                            
                           If frmGroeptekst.CheckBox6.Value = True And ffoptie <> 1 Then
                            For z = LBound(attributen) To UBound(attributen)
                            Set attribuut = attributen(z)
                             If attribuut.TagString = "GROEPTEKST" Then gp = attribuut.textstring
                              If gp = groepsnummer Then
                              If attribuut.TagString = "FLEXFIX" Then attribuut.textstring = "ja" 'FLEXFIX
                              If attribuut.TagString = "AANTAL_SLINGERS_FLEXFIX" Then attribuut.textstring = arctel3   'FLEXFIX AANTAL BOCHTEN
                              If attribuut.TagString = "FLEXFIX_AANVOER" Then attribuut.textstring = lengteaanvoer  'aanvoer flexfix groep
                              If attribuut.TagString = "FLEXFIX_RETOUR" Then attribuut.textstring = lengteretour    'retour flexfix groep
                              If attribuut.TagString = "MATNUMMER_FLEXFIX" Then attribuut.textstring = mm
                              If attribuut.TagString = "BREEDTE_FLEXFIX" Then attribuut.textstring = lang2   'FLEXFIX BREEDTE
                              If attribuut.TagString = "SL_AANVOER" Then attribuut.textstring = slingeraanvoer2 'aantal slingers aanvoer
                              If attribuut.TagString = "SL_RETOUR" Then attribuut.textstring = slingerretour2  'aantal slingers retour
                              End If
                             Next z
                            End If
                    Next I
                End If
            End If
        End If
    Next element

'   Call ThisDrawing.mflex(groepsnummer)

  '  Dim layerObj As AcadLayer
  '  If frmGroeptekst.CheckBox6 = False Then
  '  For Each layerObj In ThisDrawing.Layers
  '       If layerObj.Name = retobj.Layer Then layerObj.Name = groepsnummer
  '  Next
  '  End If
    
    If frmGroeptekst.CheckBox6 = True Then
    groepsnummer1 = groepsnummer & "_Flexfix"
    groepsnummer2 = groepsnummer & "_Flexfix_aanvoer"
    groepsnummer3 = groepsnummer & "_Flexfix_retour"
    'MsgBox groepsnummer1 & " - " & groepsnummer2 & " - " & groepsnummer3
    
    check20 = RetObj.Layer & "_Flexfix_aanvoer"
    check21 = RetObj.Layer & "_Flexfix_retour"
    check22 = myaanvoerleft(0) & "_Flexfix_aanvoerh"
    check23 = myaanvoerleft(0) & "_Flexfix_retourh"
   ' MsgBox check22 & "   -    " & check23
    
    For Each layerObj In ThisDrawing.Layers
         If layerObj.Name = RetObj.Layer Then layerObj.Name = groepsnummer1
         If layerObj.Name = check20 Then layerObj.Name = groepsnummer2
         If layerObj.Name = check21 Then layerObj.Name = groepsnummer3
         If layerObj.Name = check22 Then layerObj.Name = groepsnummer2
         If layerObj.Name = check23 Then layerObj.Name = groepsnummer3
    Next
    End If
   ' MsgBox "hier"
  
   
    Update
    End Sub
Public Function Lengte2(p1 As Variant, p2 As Variant) As Double

    'FUNCTIE VOOR HET BEREKENEN VAN DE AFSTAND TUSSEN TWEE PUNTEN
    
    Dim DX As Double
    Dim DY As Double
    
    DX = Abs(p2(0) - p1(0))
    DY = Abs(p2(1) - p1(1))

    Lengte2 = Sqr((DX ^ 2) + (DY ^ 2))
End Function

Attribute VB_Name = "M_Meten_Werkelijk"
Sub Meten_Werkelijk(RetObj, Pbase, eg)
    'Dim retobj As Object
    'Dim Pbase As Variant
    Dim element As Object
    Dim Lengte As Double
    Dim Lengte3 As Double
    Dim totallengte As String       'EBR, DEC 2002
    'Dim eg As Double         'EBR, DEC 2002: declareren van variabelen
    Dim optel As Integer            'EBR, DEC 2002: declareren van variabelen
    Dim unittel As Integer          'EBR, DEC 2002: declareren van variabelen
    Dim groepsnummer As String      'EBR, DEC 2002: declareren van variabelen
    check_layernaam = Left(RetObj.Layer, 4)
    'MsgBox check_layernaam
      
    frmGroeptekst.Hide
    'ThisDrawing.SendCommand "-layer" & vbCr & "U" & vbCr & "GT" & vbCr & vbCr
    Update
    
    'On Error Resume Next           'EBR, DEC 2002 uitgezet !
    
   '----------------------------------------------------------------
    ' BEPALEN MIDDELPUNT OF CENTERPUNT BEPALEN
    '----------------------------------------------------------------
    
    If RetObj.EntityName = "AcDbLine" Then
        Dim PBEGIN As Variant
        Dim Peind As Variant
        Dim Pmid(0 To 2) As Double
        'Dim Pmid As Variant
        
        PBEGIN = RetObj.startPoint
        Peind = RetObj.endPoint
        
        Pmid(0) = (PBEGIN(0) + Peind(0)) / 2
        Pmid(1) = (PBEGIN(1) + Peind(1)) / 2
        Pmid(2) = 0
        'Dim PUNT As AcadPoint
        'Set PUNT = ThisDrawing.ModelSpace.AddPoint(Pmid)
        'PUNT.Color = acGreen
    Else
        
        Pmid(0) = Pbase(0)
        Pmid(1) = Pbase(1)
        Pmid(2) = 0
        
    End If
    
    '----------------------------------------------------------------
    ' MAKEN SELECTIESET
    '----------------------------------------------------------------
    
        
    Dim ssetObj As AcadSelectionSet
    Dim mode As Integer
    Dim pointsArray(0 To 14) As Double
    
    'NIEUW
    'On Error Resume Next
    Set ssetObj = ThisDrawing.SelectionSets.Add("TEST_SSET")
    If Err Then ThisDrawing.SelectionSets.Item("TEST_SSET").Delete
    mode = acSelectionSetCrossingPolygon
    
    Dim tel As Integer
    Dim sHandle As String
    Dim LijnGevonden As Boolean
    Dim ArcGevonden As Boolean
    
    
Opnieuw:
    
    tel = tel + 1
    
    pointsArray(0) = Pmid(0) - tel: pointsArray(1) = Pmid(1) - tel: pointsArray(2) = 0
    pointsArray(3) = Pmid(0) + tel: pointsArray(4) = Pmid(1) - tel: pointsArray(5) = 0
    pointsArray(6) = Pmid(0) + tel: pointsArray(7) = Pmid(1) + tel: pointsArray(8) = 0
    pointsArray(9) = Pmid(0) - tel: pointsArray(10) = Pmid(1) + tel: pointsArray(11) = 0
    pointsArray(12) = Pmid(0) - tel: pointsArray(13) = Pmid(1) - tel: pointsArray(14) = 0
    
    ssetObj.SelectByPolygon mode, pointsArray
   
    '----------------------------------------------------------------
    ' LEZEN SELECTIESET
    '----------------------------------------------------------------
    
    If tel > 120 Then
        ssetObj.Clear
        ssetObj.Delete
        MsgBox "Geen juiste HOH gevonden.!!" & (Chr(13) & Chr(10)) & "Ik zoom nu uit," & Chr(13) & "wijs daarna de groep weer aan.", vbInformation
        tel = 0
        ZoomPrevious
        GoTo Opnieuw
        'End
    End If

     If ssetObj.Count > 1 Then
        
            For Each element In ssetObj
            If RetObj.Handle <> element.Handle Then
                If element.Layer = RetObj.Layer Then
                        If element.EntityName = "AcDbLine" And RetObj.EntityName = "AcDbLine" Then
                            sHandle = element.Handle
                            LijnGevonden = True
                            Exit For
                        End If
                        If element.EntityName = "AcDbArc" And RetObj.EntityName = "AcDbArc" Then
                            sHandle = element.Handle
                            ArcGevonden = True
                            Exit For
                        End If
                End If
            End If
            Next element
            
            If LijnGevonden = False And ArcGevonden = False Then GoTo Opnieuw
    Else
            GoTo Opnieuw
    End If
    
    ssetObj.Clear
    ssetObj.Delete
    
    '----------------------------------------------------------------
    ' SNIJPUNT MET LIJN BEREKENEN EN BEPALEN HOH
    '----------------------------------------------------------------
    Dim HOH As Double
       
    If RetObj.EntityName = "AcDbLine" Then
    
            Dim LijnObj As AcadLine
            Dim Peind1(0 To 2) As Double
            
            Peind1(0) = Pmid(0) + 35
            Peind1(1) = Pmid(1)
            Peind1(2) = 0
            
        
            Set LijnObj = ThisDrawing.ModelSpace.AddLine(Pmid, Peind1)
            LijnObj.Rotate Pmid, RetObj.Angle + 1.57075
                          
            Dim Ps As Variant   'snijpunt
            Dim IntersectObject As Object
            Set IntersectObject = ThisDrawing.HandleToObject(sHandle)
            
            Ps = LijnObj.IntersectWith(IntersectObject, acExtendBoth)
            
            '-------------------------------------
            'NIEUW
            '-------------------------------------
            ' weergeven van alle snijpunten
            Dim I As Integer, j As Integer, k As Integer
            Dim str As String
            If VarType(Ps) <> vbEmpty Then
                For I = LBound(Ps) To UBound(Ps)
            'uitgezet GCH  MsgBox "x=" & Round(Ps(j), 0) & Chr(10) & Chr(13) & "y=" & Round(Ps(j + 1), 0) & Chr(10) & Chr(13) & "z=" & Round(Ps(j + 2), 0), , "Snijpunt"
                    I = I + 2
                    j = j + 3
                    'k = k + 1
                Next
            End If
            
            '-------------------------------------
            LijnObj.Erase
             Dim puntobj As Object
            'uitgezet GCH  Set puntobj = ThisDrawing.ModelSpace.AddPoint(Ps)
            'uitgezet GCH  Set puntobj = ThisDrawing.ModelSpace.AddPoint(Pmid)
            ' BEPALEN HOH
            HOH = 0
            HOH = Lengte2(Ps, Pmid)
            
            
    Else
            
            'Dim puntobj2 As Object
            'puntobj2 = acMagenta
     'Set puntobj2 = ThisDrawing.ModelSpace.AddPoint(Peind1)
            
    '----------------------------------------------------------------
    ' STRAAL BEPALEN EN BEPALEN HOH
    '----------------------------------------------------------------
        
        Dim GevondenArcObj As AcadArc
        Dim ArcRadius As Double
        
        Set GevondenArcObj = ThisDrawing.HandleToObject(sHandle)
        ArcRadius = GevondenArcObj.radius
        HOH = Abs(RetObj.radius - ArcRadius)
    End If

    '----------------------------------------------------------------
    ' AFBEELDEN HOH
    '----------------------------------------------------------------
   
    HOH = Format(HOH, "0.0")
    'MsgBox HOH
    'frmGroeptekst.TextBox8 = "HOH " & HOH
    
    'EBR, DEC 2002: TOT HIER WERKT HET NU GOED !!!
    'MsgBox "EBR: v.a. hier ging het fout."
    'Exit Sub
   
    '-------------------
    'METEN VAN DE GROEP
    '-------------------
    If Err <> 0 Then
        Err.Clear
        MsgBox "Geen element geselecteerd", vbCritical, "Let op."
    Else
        For Each element In ThisDrawing.ModelSpace
              If element.Layer = RetObj.Layer Then
                'BEREKENEN TOTALE LENGTE
                If element.EntityName = "AcDbLine" Then Lengte = Lengte + element.Length
                If element.EntityName = "AcDbArc" Then Lengte = Lengte + element.ArcLength
              End If
        Next element
    End If
             z = 0
             Dim cirkel As Object
             For Each cirkel In ThisDrawing.ModelSpace
                If cirkel.Layer = RetObj.Layer Then
                If cirkel.EntityName = "AcDbCircle" Then z = z + 1
                End If
                Next cirkel
                
       If frmGroeptekst.ToggleButton1.Value = False Then wandhoogte = 2.5
       If frmGroeptekst.ToggleButton1.Value = True Then wandhoogte = 2
       If frmGroeptekst.OptionButton5 = True Then wandhoogte = frmGroeptekst.TextBox13
                
                If z <> 0 Then zlengte = (z * (100 * wandhoogte)) + 100
    
    Lengte = Lengte + zlengte
  
   'LENGTE IN METERS
    Lengte = Lengte / 100
    Lengte = Round(Lengte, 1)
    Lengte = Lengte + Val(frmGroeptekst.TextBox28) ' + 3 ' 07-04-06    <--------------------------------------------------------------------------
     
    'MsgBox "Lengte=" & Lengte, , "Ebr: tot hier werkt het goed !"
    'EBR, DEC 2002: TOT HIER WERKT HET NU GOED !!!
    ' Exit Sub
    
     
    
    zz = frmGroeptekst.Label11.Caption
    'MsgBox zz & " | " & retobj.Layer
    If zz = RetObj.Layer Then
    optel = frmGroeptekst.TextBox10        'textbox10 uitlezen
    totallengte = " "
    leegwerklengte = "ja"
    Else
    'MsgBox "eg= " & eg
    If eg = 0 Then optel = frmGroeptekst.TextBox10 'uitlezen 1e keer
    If eg <> 0 Then optel = frmGroeptekst.TextBox10 + 1 '1 erbij optellen
    totallengte = Lengte & " meter"
    leegwerklengte = "ja"
    End If
    If optel > 0 And optel < 10 Then groeponder10 = "0"
    
    unittel = frmGroeptekst.TextBox9
       
    If frmGroeptekst.CheckBox3.Value = False Then
    If unittel > 0 And unittel < 10 Then unitonder10 = "0"
    groepsnummer = "groep " & unitonder10 & frmGroeptekst.TextBox9 & "." & groeponder10 & optel    'tekst samenvoegen
    End If
    If frmGroeptekst.CheckBox3.Value = True Then
    groepsnummer = "groep " & frmGroeptekst.TextBox9 & "." & groeponder10 & optel    'tekst samenvoegen
    End If
    'groepsnummer = "groep " & frmGroeptekst.TextBox9 & "." & groeponder10 & optel  'tekst samenvoegen
    
    zz = groepsnummer
    'frmGroeptekst.Label11.Caption = Clear
    frmGroeptekst.Label11.Caption = zz
    
    eg = 1 'EERSTE GROEP
    frmGroeptekst.TextBox10 = optel
    'MsgBox optel
    
    'groepslengte op de commandregel
    zzz = groepsnummer & " = " & Lengte & " meter." & " [" & Val(frmGroeptekst.TextBox28) & "]"
    ThisDrawing.Utility.Prompt zzz
    ThisDrawing.SendCommand Chr(27)
    
       
    '-------------------------------------------------
    '  groeptekst plaatsen in de tekening
    '-------------------------------------------------
    Dim newLayer As AcadLayer
    
    
    Set newLayer = ThisDrawing.Layers.Add("GT")
    ThisDrawing.ActiveLayer = newLayer
    Update
        
    Dim hohafstand As String
    hohafstand = "H.O.H. " & HOH & " cm."
    If check_layernaam = "wand" Then hohafstand = "Wandverwarming"
    On Error Resume Next
    
    Dim Zoekpad As String
    Dim blockRefObj As Object       'EBR: var declareren
    
    ' wth
    Zoekpad = "C:\ACAD2002\DWG\groeptekstbloknew.dwg"
    
    ' ebr
    ' Zoekpad = "C:\temp\groeptekstbloknew.dwg"
    
    Set blockRefObj = ThisDrawing.ModelSpace.InsertBlock(Pbase, Zoekpad, 1, 1, 1, 0)
    
    'DOOR EBR DEC 2002:
    If Err Then
        Err.Clear
        MsgBox "symbool " & Zoekpad & " niet gevonden.", vbCritical, "Let op":
        End
    End If
    
'DOOR EBR DEC 2002: enkele aanpassingen

    Dim symbool As Object       'EBR altijd juist declareren
    Dim attributen As Variant   'EBR altijd juist declareren
    Dim attribuut As Object     'EBR altijd juist declareren
    If frmGroeptekst.OptionButton1 = True Then LW = "WTH-ZD 20*3,4 mm"
    If frmGroeptekst.OptionButton9 = True Then LW = "WTH-ZD 16*2,7 mm"
    If frmGroeptekst.OptionButton2 = True Then LW = frmGroeptekst.ComboBox4
    If frmGroeptekst.OptionButton6 = True Then LW = frmGroeptekst.ComboBox4
    If frmGroeptekst.OptionButton7 = True Then
      RL = "RM"
      Else
      RL = " "
    End If
    If frmGroeptekst.OptionButton8 = True Then
              groepsnummer = " "
              RL = "RZ"
    End If
    
    For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                         Set attribuut = attributen(I)
                         If attribuut.TagString = "RINGLEIDING" And attribuut.textstring = "" Then attribuut.textstring = RL
                         If attribuut.TagString = "LEIDINGSOORT" And attribuut.textstring = "" Then attribuut.textstring = LW
                         If attribuut.TagString = "UNITNUMMER" And attribuut.textstring = "" Then attribuut.textstring = unitonder10 & frmGroeptekst.TextBox9
                         If attribuut.TagString = "GROEPTEKST" And attribuut.textstring = "" Then attribuut.textstring = groepsnummer
                         If attribuut.TagString = "HOHAFSTAND" And attribuut.textstring = "" Then attribuut.textstring = hohafstand
                         If attribuut.TagString = "ROLLENGTE" And attribuut.textstring = "" Then attribuut.textstring = " "
                         If attribuut.TagString = "TLVL" And attribuut.textstring = "" Then attribuut.textstring = totallengte
                         If attribuut.TagString = "WERKLENGTE" And attribuut.textstring = "" Then attribuut.textstring = leegwerklengte
                         If attribuut.TagString = "WANDHOOGTE" And check_layernaam = "groe" And attribuut.textstring = "" Then attribuut.textstring = " "
                         If attribuut.TagString = "WANDHOOGTE" And check_layernaam = "wand" And attribuut.textstring = "" Then attribuut.textstring = wandhoogte & " meter hoog"
                    
                    Next I
                End If
            End If
        End If
    Next element
    
    '---layer hernoemen
    'If optel > 0 And optel < 10 Then groeponder10 = "0"
    'groepsnummer = "groep " & frmGroeptekst.TextBox9 & "." & groeponder10 & optel  'tekst samenvoegen
           
    Dim layerObj As AcadLayer
    For Each layerObj In ThisDrawing.Layers
         If layerObj.Name = RetObj.Layer Then layerObj.Name = groepsnummer
    Next
    
    
    End Sub
Public Function Lengte2(p1 As Variant, p2 As Variant) As Double

    'FUNCTIE VOOR HET BEREKENEN VAN DE AFSTAND TUSSEN TWEE PUNTEN
    
    Dim DX As Double
    Dim DY As Double
    
    DX = Abs(p2(0) - p1(0))
    DY = Abs(p2(1) - p1(1))

    Lengte2 = Sqr((DX ^ 2) + (DY ^ 2))
End Function

Attribute VB_Name = "Module1"
Sub Groeptekst()
frmGroeptekst.Show
End Sub
Sub unitlogo()
frmUnitlogo.Show
End Sub
Sub kaderlogo()
frmKaderlogo.Show
End Sub
Sub ExportXLS()
frmExportXLS.Show
End Sub
Sub inregelstaat()
frmInregelstaat.Show
End Sub
Sub Extraopties()
frmExtraopties.Show
End Sub
Sub LegrichtingFF()
frmLegrichtingFF.Show
End Sub
Sub Flexfixafstand()
frmFlexfixafstand.Show
End Sub

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
'''''Sub fopen()
'''''Dim pe2(0 To 2) As Double
'''''Dim element
'''''Dim insp
'''''
'''''For Each element In ThisDrawing.ModelSpace
'''''      If element.ObjectName = "AcDbBlockReference" Then
'''''         If element.Name = "ba3" Or element.Name = "ba2" Or element.Name = "ba1" _
'''''         Or element.Name = "ba0" Or element.Name = "ba0+" Then
'''''          insp = element.InsertionPoint
'''''
'''''          pe2(0) = insp(0)
'''''          pe2(1) = insp(1)
'''''          pe2(2) = 0
'''''          If pe2(0) <> 0 Or pe2(1) <> 0 Then
'''''          MsgBox "Je kader staat niet goed...!!!", vbCritical
'''''          element.Erase
'''''          End If
'''''          'MsgBox pe2(0) & " - " & pe2(1) & " - " & pe2(2) & " - "
'''''
'''''          End If
'''''      Update
'''''      End If
'''''     Next element
'''''End Sub

'''''Private Sub AcadDocument_BeginPlot(ByVal DrawingName As String)
'''''Dim pe2(0 To 2) As Double
'''''Dim element
'''''Dim insp
'''''
'''''For Each element In ThisDrawing.ModelSpace
'''''      If element.ObjectName = "AcDbBlockReference" Then
'''''         If element.Name = "ba3" Or element.Name = "ba2" Or element.Name = "ba1" _
'''''         Or element.Name = "ba0" Or element.Name = "ba0+" Then
'''''          insp = element.InsertionPoint
'''''
'''''          pe2(0) = insp(0)
'''''          pe2(1) = insp(1)
'''''          pe2(2) = 0
'''''          If pe2(0) <> 0 Or pe2(1) <> 0 Then
'''''          MsgBox "Je kader staat niet goed...!!!", vbCritical
'''''          element.Erase
'''''          End If
'''''          'MsgBox pe2(0) & " - " & pe2(1) & " - " & pe2(2) & " - "
'''''
'''''          End If
'''''      Update
'''''      End If
'''''     Next element
'''''
'''''End Sub

'''''Private Sub AcadDocument_BeginClose()
'''''For Each element In ThisDrawing.ModelSpace
'''''        If element.ObjectName = "AcDbBlockReference" Then
'''''            If UCase(element.Name) = "GROEPTEKSTBLOKNEW" Then
'''''                Set symbool = element
'''''                If symbool.HasAttributes Then
'''''                    attributen = symbool.GetAttributes
'''''                    For I = LBound(attributen) To UBound(attributen)
'''''                    Set attribuut = attributen(I)
'''''                      If attribuut.TagString = "FLEXFIX" And attribuut.textstring = "ja" Then
'''''                      ThisDrawing.SendCommand "ffexport" & vbCr
'''''                      Exit Sub
'''''                      End If
'''''
'''''                    Next I
'''''                End If
'''''            End If
'''''        End If
'''''    Next element
'''''End Sub
Sub papierformaatA4()
Dim element As Object
For Each element In ThisDrawing.ModelSpace
      If element.ObjectName = "AcDbBlockReference" Then
         If element.Name = "Kaderlogo" Or element.Name = "KaderlogoEngels" Or element.Name = "logotgh" Then a = a + 1
            If UCase(element.Name) = "BA2" Or UCase(element.Name) = "BA3" Or UCase(element.Name) = "BA1" _
            Or UCase(element.Name) = "BA0" Or UCase(element.Name) = "BA0+" Then element.Erase
          End If
Next element

If a > 1 Then

For Each element1 In ThisDrawing.ModelSpace
      If element1.ObjectName = "AcDbBlockReference" Then
       If element1.Name = "Kaderlogo" Or element1.Name = "KaderlogoEngels" Or element1.Name = "logotgh" Then
       Set symbool = element1
        If symbool.HasAttributes Then
        attributen = symbool.GetAttributes
        For I = LBound(attributen) To UBound(attributen)
        Set attribuut = attributen(I)
        If attribuut.TagString = "OPDRACHTGEVER" And attribuut.textstring = "" Then
          ' insp = element1.InsertionPoint
           element1.Erase
         End If
        Next I
       End If
     End If
   End If
  Next element1

For Each element2 In ThisDrawing.ModelSpace
      If element2.ObjectName = "AcDbBlockReference" Then
      If element2.Name = "Kaderlogo" Or element2.Name = "KaderlogoEngels" Or element2.Name = "logotgh" Then
      Set symbool = element2
        If symbool.HasAttributes Then
        attributen = symbool.GetAttributes
        For j = LBound(attributen) To UBound(attributen)
        Set attribuut = attributen(j)
        If attribuut.TagString = "FORMAAT" Then attribuut.textstring = "A4"  'FORMAATPAPIER
        Next j

      End If
      End If
      End If
  Next element2
Update
End If

'ThisDrawing.PurgeAll

End Sub
Sub papierformaatA3()
Dim element As Object
For Each element In ThisDrawing.ModelSpace
      If element.ObjectName = "AcDbBlockReference" Then
         If element.Name = "Kaderlogo" Or element.Name = "KaderlogoEngels" Or element.Name = "logotgh" Then a = a + 1
            If UCase(element.Name) = "BA2" Or UCase(element.Name) = "BA1" Or UCase(element.Name) = "BA4" _
            Or UCase(element.Name) = "BA0" Or UCase(element.Name) = "BA0+" Then element.Erase
          End If
Next element

If a > 1 Then

For Each element1 In ThisDrawing.ModelSpace
      If element1.ObjectName = "AcDbBlockReference" Then
       If element1.Name = "Kaderlogo" Or element1.Name = "KaderlogoEngels" Or element1.Name = "logotgh" Then
       Set symbool = element1
        If symbool.HasAttributes Then
        attributen = symbool.GetAttributes
        For I = LBound(attributen) To UBound(attributen)
        Set attribuut = attributen(I)
        If attribuut.TagString = "OPDRACHTGEVER" And attribuut.textstring = "" Then
          ' insp = element1.InsertionPoint
           element1.Erase
         End If
        Next I
       End If
     End If
   End If
  Next element1

For Each element2 In ThisDrawing.ModelSpace
      If element2.ObjectName = "AcDbBlockReference" Then
      If element2.Name = "Kaderlogo" Or element2.Name = "KaderlogoEngels" Or element2.Name = "logotgh" Then
      Set symbool = element2
        If symbool.HasAttributes Then
        attributen = symbool.GetAttributes
        For j = LBound(attributen) To UBound(attributen)
        Set attribuut = attributen(j)
        If attribuut.TagString = "FORMAAT" Then attribuut.textstring = "A3"  'FORMAATPAPIER
        Next j

      End If
      End If
      End If
  Next element2
Update
End If

'ThisDrawing.PurgeAll

End Sub
Sub papierformaatA2()

Dim element As Object
For Each element In ThisDrawing.ModelSpace
      If element.ObjectName = "AcDbBlockReference" Then
         If element.Name = "Kaderlogo" Or element.Name = "KaderlogoEngels" Or element.Name = "logotgh" Then a = a + 1
            If UCase(element.Name) = "BA1" Or UCase(element.Name) = "BA3" Or UCase(element.Name) = "BA4" _
            Or UCase(element.Name) = "BA0" Or UCase(element.Name) = "BA0+" Then element.Erase
          End If
Next element

If a > 1 Then

For Each element1 In ThisDrawing.ModelSpace
      If element1.ObjectName = "AcDbBlockReference" Then
       If element1.Name = "Kaderlogo" Or element1.Name = "KaderlogoEngels" Or element1.Name = "logotgh" Then
       Set symbool = element1
        If symbool.HasAttributes Then
        attributen = symbool.GetAttributes
        For I = LBound(attributen) To UBound(attributen)
        Set attribuut = attributen(I)
        If attribuut.TagString = "OPDRACHTGEVER" And attribuut.textstring = "" Then
          ' insp = element1.InsertionPoint
           element1.Erase
         End If
        Next I
       End If
     End If
   End If
  Next element1

For Each element2 In ThisDrawing.ModelSpace
      If element2.ObjectName = "AcDbBlockReference" Then
      If element2.Name = "Kaderlogo" Or element2.Name = "KaderlogoEngels" Or element2.Name = "logotgh" Then
      Set symbool = element2
        If symbool.HasAttributes Then
        attributen = symbool.GetAttributes
        For j = LBound(attributen) To UBound(attributen)
        Set attribuut = attributen(j)
        If attribuut.TagString = "FORMAAT" Then attribuut.textstring = "A2"  'FORMAATPAPIER
        Next j

      End If
      End If
      End If
  Next element2
Update
End If

'ThisDrawing.PurgeAll

End Sub
Sub papierformaatA1()

Dim element As Object
For Each element In ThisDrawing.ModelSpace
      If element.ObjectName = "AcDbBlockReference" Then
         If element.Name = "Kaderlogo" Or element.Name = "KaderlogoEngels" Or element.Name = "logotgh" Then a = a + 1
            If UCase(element.Name) = "BA2" Or UCase(element.Name) = "BA3" Or UCase(element.Name) = "BA4" _
            Or UCase(element.Name) = "BA0" Or UCase(element.Name) = "BA0+" Then element.Erase
          End If
Next element


If a > 1 Then

For Each element1 In ThisDrawing.ModelSpace
      If element1.ObjectName = "AcDbBlockReference" Then
       If element1.Name = "Kaderlogo" Or element1.Name = "KaderlogoEngels" Or element1.Name = "logotgh" Then
       Set symbool = element1
        If symbool.HasAttributes Then
        attributen = symbool.GetAttributes
        For I = LBound(attributen) To UBound(attributen)
        Set attribuut = attributen(I)
        If attribuut.TagString = "OPDRACHTGEVER" And attribuut.textstring = "" Then
          ' insp = element1.InsertionPoint
           element1.Erase
         End If
        Next I
       End If
     End If
   End If
  Next element1

For Each element2 In ThisDrawing.ModelSpace
      If element2.ObjectName = "AcDbBlockReference" Then
      If element2.Name = "Kaderlogo" Or element2.Name = "KaderlogoEngels" Or element2.Name = "logotgh" Then
      Set symbool = element2
        If symbool.HasAttributes Then
        attributen = symbool.GetAttributes
        For j = LBound(attributen) To UBound(attributen)
        Set attribuut = attributen(j)
        If attribuut.TagString = "FORMAAT" Then attribuut.textstring = "A1"  'FORMAATPAPIER
        Next j

      End If
      End If
      End If
  Next element2
Update
End If

'ThisDrawing.PurgeAll




' -------!!!!!!!!!!!!!!!!!!!! DIT STUK EFFE BEWAREN VOOR ALS HET BOVENSTAANDE FOUT GAAT !!!!!!!!!!!!!!!!!!!!-----
'For Each element2 In ThisDrawing.ModelSpace
'      If element2.ObjectName = "AcDbBlockReference" Then
'      If UCase(element2.Name) = "KADERLOGO" Or UCase(element2.Name) = "LOGOTGH" Then
'      Set symbool = element2
'        If symbool.HasAttributes Then
'        attributen = symbool.GetAttributes
'        For I = LBound(attributen) To UBound(attributen)
'        Set attribuut = attributen(I)
'        If attribuut.TagString = "FORMAAT" Then attribuut.TextString = "A1"  'FORMAATPAPIER
'        Next I
'
'      End If
'      End If
'      End If
'  Next element2
'Update
End Sub
Sub papierformaatA0()
Dim element As Object
For Each element In ThisDrawing.ModelSpace
      If element.ObjectName = "AcDbBlockReference" Then
         If element.Name = "Kaderlogo" Or element.Name = "KaderlogoEngels" Or element.Name = "logotgh" Then a = a + 1
            If UCase(element.Name) = "BA2" Or UCase(element.Name) = "BA3" Or UCase(element.Name) = "BA4" _
            Or UCase(element.Name) = "BA1" Or UCase(element.Name) = "BA0+" Then element.Erase
          End If
Next element

If a > 1 Then

For Each element1 In ThisDrawing.ModelSpace
      If element1.ObjectName = "AcDbBlockReference" Then
       If element1.Name = "Kaderlogo" Or element1.Name = "KaderlogoEngels" Or element1.Name = "logotgh" Then
       Set symbool = element1
        If symbool.HasAttributes Then
        attributen = symbool.GetAttributes
        For I = LBound(attributen) To UBound(attributen)
        Set attribuut = attributen(I)
        If attribuut.TagString = "OPDRACHTGEVER" And attribuut.textstring = "" Then
          ' insp = element1.InsertionPoint
           element1.Erase
         End If
        Next I
       End If
     End If
   End If
  Next element1

For Each element2 In ThisDrawing.ModelSpace
      If element2.ObjectName = "AcDbBlockReference" Then
      If element2.Name = "Kaderlogo" Or element2.Name = "KaderlogoEngels" Or element2.Name = "logotgh" Then
      Set symbool = element2
        If symbool.HasAttributes Then
        attributen = symbool.GetAttributes
        For j = LBound(attributen) To UBound(attributen)
        Set attribuut = attributen(j)
        If attribuut.TagString = "FORMAAT" Then attribuut.textstring = "A0"  'FORMAATPAPIER
        Next j

      End If
      End If
      End If
  Next element2
Update
End If


'ThisDrawing.PurgeAll

End Sub
Sub papierformaatA0plus()
Dim element As Object
For Each element In ThisDrawing.ModelSpace
      If element.ObjectName = "AcDbBlockReference" Then
         If element.Name = "Kaderlogo" Or element.Name = "KaderlogoEngels" Or element.Name = "logotgh" Then a = a + 1
            If UCase(element.Name) = "BA2" Or UCase(element.Name) = "BA3" Or UCase(element.Name) = "BA4" _
            Or UCase(element.Name) = "BA0" Or UCase(element.Name) = "BA1" Then element.Erase
          End If
Next element

If a > 1 Then

For Each element1 In ThisDrawing.ModelSpace
      If element1.ObjectName = "AcDbBlockReference" Then
       If element1.Name = "Kaderlogo" Or element1.Name = "KaderlogoEngels" Or element1.Name = "logotgh" Then
       Set symbool = element1
        If symbool.HasAttributes Then
        attributen = symbool.GetAttributes
        For I = LBound(attributen) To UBound(attributen)
        Set attribuut = attributen(I)
        If attribuut.TagString = "OPDRACHTGEVER" And attribuut.textstring = "" Then
          ' insp = element1.InsertionPoint
           element1.Erase
         End If
        Next I
       End If
     End If
   End If
  Next element1

For Each element2 In ThisDrawing.ModelSpace
      If element2.ObjectName = "AcDbBlockReference" Then
      If element2.Name = "Kaderlogo" Or element2.Name = "KaderlogoEngels" Or element2.Name = "logotgh" Then
      Set symbool = element2
        If symbool.HasAttributes Then
        attributen = symbool.GetAttributes
        For j = LBound(attributen) To UBound(attributen)
        Set attribuut = attributen(j)
        If attribuut.TagString = "FORMAAT" Then attribuut.textstring = "A0+"  'FORMAATPAPIER
        Next j

      End If
      End If
      End If
  Next element2
Update
End If

'ThisDrawing.PurgeAll


End Sub
Sub mflex(groepsnummer)

   On Error Resume Next
   Dim RetObj As Object
   Dim Pbase As Variant
   Dim element As Object
   Dim Lengte As Double
   Dim Lengte1 As Double
   Dim lengte20 As Double
   Dim Lengte3 As Double
   
    Lengte = 0
    Lengte1 = 0
    lengte20 = 0
    Lengte3 = 0

RetObj = groepsnummer
    'ThisDrawing.Utility.GetEntity RetObj, Pbase, "Selecteer het MAT-PATROON."
'    If Err <> 0 Then
'        Err.Clear
'        message = "Mis"
'        ThisDrawing.Utility.Prompt message
'        ThisDrawing.SendCommand Chr(27)
'
'        Exit Sub
'        'End
'    End If


'MsgBox RetObj.Layer
   ' aktievelaag = retobj.layer   'ThisDrawing.Utility.GetEntity RetObj, Pbase, "Selecteer een lijn of cirkelboog"
   ' If Err Then
   '     Err.Clear
   '     'OPNIEUW OF STOPPEN
   '     GoTo Opnieuw
   '     'Exit sub
   checkpoint1 = Right(RetObj.Layer, 4)
   If checkpoint1 = "voer" Then
      checkpoint2 = Len(RetObj.Layer)
      checkpoint3 = checkpoint2 - 16
      checkpoint4 = Left(RetObj.Layer, checkpoint3)
      Set newLayer = ThisDrawing.Layers.Add(checkpoint4)
      ThisDrawing.ActiveLayer = newLayer
      zetlaagterug = RetObj.Layer
      'MsgBox checkpoint4
   End If
      If checkpoint1 = "tour" Then
      checkpoint2 = Len(RetObj.Layer)
      checkpoint3 = checkpoint2 - 15
      checkpoint4 = Left(RetObj.Layer, checkpoint3)
      Set newLayer = ThisDrawing.Layers.Add(checkpoint4)
      ThisDrawing.ActiveLayer = newLayer
      zetlaagterug = RetObj.Layer
      'MsgBox checkpoint4
   End If
   zetlaagterug = RetObj.Layer
   
   'retobj.layer = ThisDrawing.ActiveLayer.Name
     'If checkpoint1 <> "voer" And checkpoint1 <> "tour" Then
        For Each element In ThisDrawing.ModelSpace
            If element.Layer = RetObj.Layer Then
                'BEREKENEN TOTALE LENGTE
                If element.EntityName = "AcDbLine" Then Lengte = Lengte + element.Length
                If element.EntityName = "AcDbArc" Then Lengte = Lengte + element.ArcLength
                If element.EntityName = "AcDbPolyline" Then Lengte = Lengte + element.Length
                
            End If
        Next element
     'End If
    
    Lengte = Lengte / 100
    Lengte = Round(Lengte, 1)
    
    If checkpoint1 = "xfix" Then
        samen100 = "_aanvoer"
        Else
        samen100 = "_Flexfix_aanvoer"
    End If
    
    
    checkpointh = Right(RetObj.Layer, 1)
    If checkpointh = "h" Then
         checkpoint20 = Len(RetObj.Layer)
         checkpoint20 = checkpoint20 - 1
         checkpointh2 = Left(RetObj.Layer, checkpoint20)
            If checkpoint1 = "fixh" Then
            samen100 = "_aanvoerh"
            Else
            samen100 = "_Flexfix_aanvoerh"
            End If
         samenvoeging1 = checkpointh2 & samen100
    End If
    
    If checkpointh <> "h" Then samenvoeging1 = RetObj.Layer & samen100
    
    
    
    
    'If checkpoint1 = "voer" Then
         For Each element In ThisDrawing.ModelSpace
            If element.Layer = samenvoeging1 Then '(RetObj.Layer & samen100) Then
                'BEREKENEN TOTALE LENGTE
                If element.EntityName = "AcDbLine" Then Lengte1 = Lengte1 + element.Length
                If element.EntityName = "AcDbArc" Then Lengte1 = Lengte1 + element.ArcLength
                If element.EntityName = "AcDbPolyline" Then Lengte1 = Lengte1 + element.Length
                
            End If
     Next element
     'End If
    Lengte1 = Lengte1 / 100
    Lengte1 = Round(Lengte1, 1)
    
    If checkpoint1 = "xfix" Then
        samen100 = "_retour"
        Else
        samen100 = "_Flexfix_retour"
    End If
    
    
     If checkpointh = "h" Then
            If checkpoint1 = "fixh" Then
            samen100 = "_retourh"
            Else
            samen100 = "_Flexfix_retourh"
            End If
         samenvoeging2 = checkpointh2 & samen100
     End If
    
     If checkpointh <> "h" Then samenvoeging2 = RetObj.Layer & samen100
     
    
    'If checkpoint1 = "tour" Then
         For Each element In ThisDrawing.ModelSpace
            If element.Layer = samenvoeging2 Then '(RetObj.Layer & samen100) Then
                'BEREKENEN TOTALE LENGTE
                If element.EntityName = "AcDbLine" Then lengte20 = lengte20 + element.Length
                If element.EntityName = "AcDbArc" Then lengte20 = lengte20 + element.ArcLength
                If element.EntityName = "AcDbPolyline" Then lengte20 = lengte20 + element.Length
                
            End If
     Next element
     'End If
    lengte20 = lengte20 / 100
    lengte20 = Round(lengte20, 1)
    Lengte3 = Lengte + Lengte1 + lengte20
    
    zzz1 = (Chr(13) & Chr(10)) & "De lengte van het mat-patroon: " & Lengte & " meter(s)" & " [" & zetlaagterug & "]" & (Chr(13) & Chr(10)) _
    & "Aanvoerlengte van het mat-patroon: " & Lengte1 & " meter(s)" & (Chr(13) & Chr(10)) _
    & "Retourlengte van het mat-patroon: " & lengte20 & " meter(s)" & (Chr(13) & Chr(10)) _
    & "Totale lengte: " & Lengte3 & " meter(s)"
    
    'MsgBox Lengte & " meter(s)" & " | De lengte van het mat-patroon." & (Chr(13) & Chr(10)) & (Chr(13) & Chr(10)) _
    '& lengte1 & " meter(s)" & " | Aanvoerlengte van het mat-patroon. " & (Chr(13) & Chr(10)) _
    '& lengte20 & " meter(s)" & " | Retourlengte van het mat-patroon. " & (Chr(13) & Chr(10)) & (Chr(13) & Chr(10)) _
    '& "Totale lengte = " & lengte3, vbInformation, "Laag: " & aktievelaag   'RetObj.Layer
    Lengte = 0
    Lengte1 = 0
    lengte20 = 0
    Lengte3 = 0

    ThisDrawing.Utility.Prompt zzz1
    ThisDrawing.SendCommand Chr(27)

      Set newLayer = ThisDrawing.Layers.Add(zetlaagterug)
      ThisDrawing.ActiveLayer = newLayer

  End Sub

Attribute VB_Name = "Unitblok"
Sub Unitblok(aantal_groepen, pb2, bestand2, bestand3, scaal)

  Set blockRefObj = ThisDrawing.ModelSpace.InsertBlock(pb2, bestand2, scaal, scaal, 1, 0)
  Update
  
If frmGroeptekst.OptionButton7 = True Or frmGroeptekst.OptionButton8 = True Or ComboBox2 = "RINGLEIDING" Then
 afmunitRING = "RINGLEIDING"
Else


 'open text bestand om afmetingen van de unit uit te lezen
  aantal_groepen2 = aantal_groepen
Const ForReading = 1, ForWriting = 2, ForAppending = 3
Const TristateUseDefault = -2, TristateTrue = -1, TristateFalse = 0
Dim fs, a, afmunit
Set fs = CreateObject("Scripting.FileSystemObject")
Set a = fs.OpenTextFile(bestand3, ForReading, False)
Do While aantal_groepen2 <> 0
    afmunit = a.ReadLine
    aantal_groepen2 = aantal_groepen2 - 1
Loop
a.Close 'sluiten van tekstbestand
End If
 


unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If


Dim element4 As Object
unit = frmGroeptekst.ComboBox2
If frmGroeptekst.ComboBox2 = "RUW-Groot" Then unit = "RUW"
If frmGroeptekst.ComboBox2 = "RUW-Klein" Then unit = "RUW"
If frmGroeptekst.ComboBox2 = "RUB-R" And aantal_groepen > 4 Then unit = "RUH-R"
If frmGroeptekst.ComboBox2 = "RUB-RT" And aantal_groepen > 4 Then unit = "RUH-RT"
If frmGroeptekst.ComboBox2 = "RUB-S" And aantal_groepen > 0 Then unit = "RUH-S"
If frmGroeptekst.ComboBox2 = "VSKO" Then unit = "VSKO-B"

For Each element4 In ThisDrawing.ModelSpace
      If element4.ObjectName = "AcDbBlockReference" Then
      If UCase(element4.Name) = unit Then
      Set symbool = element4
        If symbool.HasAttributes Then
        attributen = symbool.GetAttributes
        For I = LBound(attributen) To UBound(attributen)
        Set attribuut = attributen(I)
        If unit = "RINGLEIDING" Then
        If attribuut.TagString = "AFMETINGEN" And attribuut.textstring = "" Then attribuut.textstring = afmunitRING 'AFMETING VAN DEUNIT
        Else
        If attribuut.TagString = "AFMETINGEN" And attribuut.textstring = "" Then attribuut.textstring = afmunit 'AFMETING VAN DEUNIT
        End If
        If attribuut.TagString = "UNITNUMMER" And attribuut.textstring = "" Then attribuut.textstring = unitonder10 'UNITNUMMER
        Next I
       End If
      End If
      End If
 Next element4
End Sub

Attribute VB_Name = "Update_module"
Sub update_unitlogo()
On Error Resume Next
If frmGroeptekst.ComboBox2 = "" Then
    MsgBox "Je bent 'Type unit' vergeten in te vullen..!!"
    frmGroeptekst.ComboBox2.SetFocus
    Exit Sub
    End If
If frmGroeptekst.ComboBox1 = "" Then
    MsgBox "Je bent 'Bevestigingsmateriaal' vergeten in te vullen..!!"
    frmGroeptekst.ComboBox1.SetFocus
    Exit Sub
    End If
If frmGroeptekst.ComboBox4 = "" And frmGroeptekst.OptionButton6 = True Then
    MsgBox "Je bent 'Type buis' vergeten in te vullen..!!"
    frmGroeptekst.ComboBox4.SetFocus
    Exit Sub
    End If
If frmGroeptekst.ComboBox4 = "" And frmGroeptekst.OptionButton2 = True Then
    MsgBox "Je bent 'Type buis' vergeten in te vullen..!!"
    frmGroeptekst.ComboBox4.SetFocus
    Exit Sub
    End If
frmGroeptekst.Hide
frmGroeptekst.TextBox9.Locked = False
    Set newLayer = ThisDrawing.Layers.Add("BLOKLOGO")
    ThisDrawing.ActiveLayer = newLayer
    Update
    ThisDrawing.SendCommand "-layer" & vbCr & "U" & vbCr & "*" & vbCr & vbCr
    Update
Call frmGroeptekst.Schaal(scaal)
If frmGroeptekst.OptionButton1.Value = True And (frmGroeptekst.TextBox11 = "0" And frmGroeptekst.TextBox25 <> "0") Then
bestand = "c:\acad2002\dwg\Mat_spe_FLEX.dwg"
'MsgBox bestand
Else
bestand = "c:\acad2002\dwg\Mat_spe_ZD.dwg"
End If


unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If


For Each element10 In ThisDrawing.ModelSpace
      If element10.ObjectName = "AcDbBlockReference" Then
       If UCase(element10.Name) = "HERZ" Or UCase(element10.Name) = "KMV" Or UCase(element10.Name) = "RUH-N" _
       Or UCase(element10.Name) = "RUH-R" Or UCase(element10.Name) = "RUH-RT" Or UCase(element10.Name) = "RUB-R" _
       Or UCase(element10.Name) = "RUB-RT" Or UCase(element10.Name) = "RUBK-R" Or UCase(element10.Name) = "RUBK-RT" _
       Or UCase(element10.Name) = "LT" Or UCase(element10.Name) = "LT-N" Or UCase(element10.Name) = "LTS" _
       Or UCase(element10.Name) = "LT-VK" Or UCase(element10.Name) = "RINGLEIDING" Or UCase(element10.Name) = "RU-WW" _
       Or UCase(element10.Name) = "RUV" Or UCase(element10.Name) = "RUH-S" Or UCase(element10.Name) = "RUB-S" _
       Or UCase(element10.Name) = "VSKO" Or UCase(element10.Name) = "LTS-N" Or UCase(element10.Name) = "RU-WWN" _
       Or UCase(element10.Name) = "RU-WWS" Or UCase(element10.Name) = "RU-WK" Or UCase(element10.Name) = "RU-WKN" Or UCase(element10.Name) = "RU-WKS" Then
       Set symbool = element10
        If symbool.HasAttributes Then
        attributen = symbool.GetAttributes
        For I = LBound(attributen) To UBound(attributen)
        Set attribuut = attributen(I)
         If attribuut.TagString = "UNITNUMMER" And attribuut.textstring <> "" Then aa = attribuut.textstring 'UNITNUMMER
        
          If aa = unitonder10 Then
           insp = element10.InsertionPoint
           'element10.Highlight (True)
           element10.Erase
           aa = ""
          End If
        Next I
       End If
     End If
   End If
  Next element10


 
  

If frmGroeptekst.OptionButton2.Value = True Then bestand = "c:\acad2002\dwg\Mat_spe_PE.dwg"
If frmGroeptekst.OptionButton6.Value = True Then bestand = "c:\acad2002\dwg\Mat_spe_ALU.dwg"
If frmGroeptekst.OptionButton1.Value = True And (frmGroeptekst.OptionButton7 = True Or frmGroeptekst.OptionButton8 = True) Then bestand = "c:\acad2002\dwg\Mat_spe_ZDringleiding.dwg"
If frmGroeptekst.OptionButton2.Value = True And (frmGroeptekst.OptionButton7 = True Or frmGroeptekst.OptionButton8 = True) Then bestand = "c:\acad2002\dwg\Mat_spe_PEringleiding.dwg"
If frmGroeptekst.OptionButton6.Value = True And (frmGroeptekst.OptionButton7 = True Or frmGroeptekst.OptionButton8 = True) Then bestand = "c:\acad2002\dwg\Mat_spe_ALUringleiding.dwg"
bestand20 = "c:\acad2002\dwg\Mat_spe_FLEX_Aankoppel.dwg"
Update

If Err Then
    frmGroeptekst.Show
    Exit Sub
    End If
Dim element2 As Object
If frmGroeptekst.OptionButton1.Value = True Then
aantal_groepen = (Val(frmGroeptekst.TextBox1)) + (Val(frmGroeptekst.TextBox2)) + (Val(frmGroeptekst.TextBox3)) + (Val(frmGroeptekst.TextBox4)) + (Val(frmGroeptekst.TextBox5)) + _
(Val(frmGroeptekst.TextBox6)) + (Val(frmGroeptekst.TextBox7)) + (Val(frmGroeptekst.TextBox15)) + (Val(frmGroeptekst.TextBox16)) + (Val(frmGroeptekst.TextBox17))
If (Val(frmGroeptekst.TextBox1)) = 0 Then frmGroeptekst.TextBox1 = "-"
If (Val(frmGroeptekst.TextBox2)) = 0 Then frmGroeptekst.TextBox2 = "-"
If (Val(frmGroeptekst.TextBox3)) = 0 Then frmGroeptekst.TextBox3 = "-"
If (Val(frmGroeptekst.TextBox4)) = 0 Then frmGroeptekst.TextBox4 = "-"
If (Val(frmGroeptekst.TextBox5)) = 0 Then frmGroeptekst.TextBox5 = "-"
If (Val(frmGroeptekst.TextBox6)) = 0 Then frmGroeptekst.TextBox6 = "-"
If (Val(frmGroeptekst.TextBox7)) = 0 Then frmGroeptekst.TextBox7 = "-"
If (Val(frmGroeptekst.TextBox15)) = 0 Then frmGroeptekst.TextBox15 = "-"
If (Val(frmGroeptekst.TextBox16)) = 0 Then frmGroeptekst.TextBox16 = "-"
aantal_groepen = aantal_groepen + (Val(frmGroeptekst.TextBox26))
'MsgBox aantal_groepen
If frmGroeptekst.ComboBox3.Enabled = False Then
REGELTYPE = frmGroeptekst.ComboBox2 & " " & aantal_groepen 'ZONDER REGELING
Else
REGELTYPE = frmGroeptekst.ComboBox2 & " " & aantal_groepen & "/" & frmGroeptekst.ComboBox3 'met regeling
End If
If frmGroeptekst.OptionButton7 = True Or frmGroeptekst.OptionButton8 = True Then REGELTYPE = frmGroeptekst.ComboBox2

If frmGroeptekst.ComboBox2 = "RUW-Groot" Or frmGroeptekst.ComboBox2 = "RUW-Klein" Then
REGELTYPE = "RUW" & " " & aantal_groepen
End If
'bloklogo invullen WTH-ZD
  
unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element2 In ThisDrawing.ModelSpace
      If element2.ObjectName = "AcDbBlockReference" Then
      If UCase(element2.Name) = "MAT_SPE_ZD" Or UCase(element2.Name) = "MAT_SPE_ZDRINGLEIDING" Or UCase(element2.Name) = "MAT_SPE_ZD_1627" Then
      Set symbool = element2
        If symbool.HasAttributes Then
        attributen = symbool.GetAttributes
        For I = LBound(attributen) To UBound(attributen)
        Set attribuut = attributen(I)
        If attribuut.TagString = "RNU" And attribuut.textstring <> "" Then bb = attribuut.textstring 'REGELUNITNUMMER
            If bb = unitonder10 Then
              For k = LBound(attributen) To UBound(attributen)
              Set attribuut = attributen(k)
              'element2.Highlight (True)
              If attribuut.TagString = "WTHZD" And attribuut.textstring <> "" Then attribuut.textstring = "WTH-ZD 20*3,4 mm" 'REGELUNITNUMMER
              If attribuut.TagString = "WTH250" And attribuut.textstring <> "" Then attribuut.textstring = frmGroeptekst.TextBox1  '250 METER
              If attribuut.TagString = "WTH165" And attribuut.textstring <> "" Then attribuut.textstring = frmGroeptekst.TextBox2  '165 METER
              If attribuut.TagString = "WTH125" And attribuut.textstring <> "" Then attribuut.textstring = frmGroeptekst.TextBox3  '125 METER
              If attribuut.TagString = "WTH105" And attribuut.textstring <> "" Then attribuut.textstring = frmGroeptekst.TextBox4  '105 METER
              If attribuut.TagString = "WTH90" And attribuut.textstring <> "" Then attribuut.textstring = frmGroeptekst.TextBox5  '90 METER
              If attribuut.TagString = "WTH75" And attribuut.textstring <> "" Then attribuut.textstring = frmGroeptekst.TextBox6  '75 METER
              If attribuut.TagString = "WTH63" And attribuut.textstring <> "" Then attribuut.textstring = frmGroeptekst.TextBox7  '63 METER
              If attribuut.TagString = "WTH50" And attribuut.textstring <> "" Then attribuut.textstring = frmGroeptekst.TextBox15  '40 METER
              If attribuut.TagString = "WTH40" And attribuut.textstring <> "" Then attribuut.textstring = frmGroeptekst.TextBox16  '50 METER
              If attribuut.TagString = "REGELUNITTYPE" And attribuut.textstring <> "" Then attribuut.textstring = REGELTYPE 'TYPE REGELUNIT
              If attribuut.TagString = "BEVESTIGINGSTYPE" And attribuut.textstring <> "" Then attribuut.textstring = frmGroeptekst.ComboBox1   'BEVESTIGING
              'If attribuut.TagString = "ROLGROTER250" And CheckBox1.Value = True Then attribuut.TextString = frmGroeptekst.TextBox14 & " meter :" 'ROL GROTER DAN 250 METER
              Next k
             bb = ""
             End If
       Next I
       
      End If
      End If
      End If
  Next element2
 End If

Dim ELEMENT7
If frmGroeptekst.OptionButton9.Value = True Then
aantal_groepen = (Val(frmGroeptekst.TextBox4)) + (Val(frmGroeptekst.TextBox5)) + _
(Val(frmGroeptekst.TextBox6)) + (Val(frmGroeptekst.TextBox7)) + (Val(frmGroeptekst.TextBox17))
If (Val(frmGroeptekst.TextBox4)) = 0 Then frmGroeptekst.TextBox4 = "-"
If (Val(frmGroeptekst.TextBox5)) = 0 Then frmGroeptekst.TextBox5 = "-"
If (Val(frmGroeptekst.TextBox6)) = 0 Then frmGroeptekst.TextBox6 = "-"
If (Val(frmGroeptekst.TextBox7)) = 0 Then frmGroeptekst.TextBox7 = "-"
aantal_groepen = aantal_groepen + (Val(frmGroeptekst.TextBox26))
'MsgBox aantal_groepen
If frmGroeptekst.ComboBox3.Enabled = False Then
REGELTYPE = frmGroeptekst.ComboBox2 & " " & aantal_groepen 'ZONDER REGELING
Else
REGELTYPE = frmGroeptekst.ComboBox2 & " " & aantal_groepen & "/" & frmGroeptekst.ComboBox3 'met regeling
End If
If frmGroeptekst.OptionButton7 = True Or frmGroeptekst.OptionButton8 = True Then REGELTYPE = frmGroeptekst.ComboBox2

If frmGroeptekst.ComboBox2 = "RUW-Groot" Or frmGroeptekst.ComboBox2 = "RUW-Klein" Then
REGELTYPE = "RUW" & " " & aantal_groepen
End If
'bloklogo invullen WTH-ZD 16*2,7
  
unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If



For Each ELEMENT7 In ThisDrawing.ModelSpace
      If ELEMENT7.ObjectName = "AcDbBlockReference" Then
      If UCase(ELEMENT7.Name) = "MAT_SPE_ZD_1627" Then
      Set symbool = ELEMENT7
        If symbool.HasAttributes Then
        attributen = symbool.GetAttributes
        For I = LBound(attributen) To UBound(attributen)
        Set attribuut = attributen(I)
        If attribuut.TagString = "RNU" And attribuut.textstring <> "" Then bb = attribuut.textstring 'REGELUNITNUMMER
            If bb = unitonder10 Then
              For k = LBound(attributen) To UBound(attributen)
              Set attribuut = attributen(k)
              'ELEMENT7.Highlight (True)
              If attribuut.TagString = "WTHZD" And attribuut.textstring <> "" Then attribuut.textstring = "WTH-ZD 16 * 2,7 mm" 'REGELUNITNUMMER
              If attribuut.TagString = "WTH105" And attribuut.textstring <> "" Then attribuut.textstring = frmGroeptekst.TextBox4  '105 METER
              If attribuut.TagString = "WTH90" And attribuut.textstring <> "" Then attribuut.textstring = frmGroeptekst.TextBox5  '90 METER
              If attribuut.TagString = "WTH75" And attribuut.textstring <> "" Then attribuut.textstring = frmGroeptekst.TextBox6  '75 METER
              If attribuut.TagString = "WTH63" And attribuut.textstring <> "" Then attribuut.textstring = frmGroeptekst.TextBox7  '63 METER
              If attribuut.TagString = "REGELUNITTYPE" And attribuut.textstring <> "" Then attribuut.textstring = REGELTYPE 'TYPE REGELUNIT
              If attribuut.TagString = "BEVESTIGINGSTYPE" And attribuut.textstring <> "" Then attribuut.textstring = frmGroeptekst.ComboBox1   'BEVESTIGING
              'If attribuut.TagString = "ROLGROTER250" And CheckBox1.Value = True Then attribuut.TextString = frmGroeptekst.TextBox14 & " meter :" 'ROL GROTER DAN 250 METER
              Next k
             bb = ""
             End If
       Next I
       
      End If
      End If
      End If
  Next ELEMENT7
  
 End If

 For Each element6 In ThisDrawing.ModelSpace
      If element6.ObjectName = "AcDbBlockReference" Then
      If UCase(element6.Name) = "MAT_SPE_FLEX" Or element6.Name = "Mat_spe_FLEX_Aankoppel" Then
      Set symbool = element6
        If symbool.HasAttributes Then
        attributen = symbool.GetAttributes
        For I = LBound(attributen) To UBound(attributen)
        Set attribuut = attributen(I)
        
        If attribuut.TagString = "RNU" And attribuut.textstring <> "" Then bb = attribuut.textstring 'REGELUNITNUMMER
            If bb = unitonder10 Then
              For k = LBound(attributen) To UBound(attributen)
              Set attribuut = attributen(k)
                'element6.Highlight (True)
                'If attribuut.TagString = "RNU" And attribuut.TextString <> "" Then attribuut.TextString = unitonder10 'REGELUNITNUMMER
                If attribuut.TagString = "FLEX_BUIS" And attribuut.textstring <> "" Then attribuut.textstring = "WTH-ZD 16 * 2,7 mm" 'REGELUNITNUMMER
                If attribuut.TagString = "FLEX_METERS" And attribuut.textstring <> "" Then attribuut.textstring = frmGroeptekst.TextBox25  'AANTAL METER
                If attribuut.TagString = "FLEX_MATTEN" And attribuut.textstring <> "" Then attribuut.textstring = frmGroeptekst.TextBox26  'AANTAL METER
                If attribuut.TagString = "REGELUNITTYPE" And attribuut.textstring <> "" Then attribuut.textstring = REGELTYPE  'TYPE REGELUNIT
                If attribuut.TagString = "BEVESTIGINGSTYPE" And attribuut.textstring <> "" Then attribuut.textstring = frmGroeptekst.ComboBox1  'BEVESTIGING
             Next k
             bb = ""
           End If
       
       
       Next I
       
      End If
      End If
      End If
  Next element6

 Update
 
 Dim element3 As Object
If frmGroeptekst.OptionButton2.Value = True Then
aantal_groepen = (Val(frmGroeptekst.TextBox1)) + (Val(frmGroeptekst.TextBox2)) + (Val(frmGroeptekst.TextBox3)) + (Val(frmGroeptekst.TextBox17))
If (Val(frmGroeptekst.TextBox1)) = 0 Then frmGroeptekst.TextBox1 = "-"
If (Val(frmGroeptekst.TextBox2)) = 0 Then frmGroeptekst.TextBox2 = "-"
If (Val(frmGroeptekst.TextBox3)) = 0 Then frmGroeptekst.TextBox3 = "-"
If frmGroeptekst.ComboBox3.Enabled = False Then
REGELTYPE = frmGroeptekst.ComboBox2 & " " & aantal_groepen
Else
REGELTYPE = frmGroeptekst.ComboBox2 & " " & aantal_groepen & "/" & frmGroeptekst.ComboBox3
End If
If frmGroeptekst.OptionButton7 = True Or frmGroeptekst.OptionButton8 = True Then REGELTYPE = frmGroeptekst.ComboBox2

'PE-RT
unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element3 In ThisDrawing.ModelSpace
      If element3.ObjectName = "AcDbBlockReference" Then
      If UCase(element3.Name) = "MAT_SPE_PE" Or element3.Name = "Mat_spe_PEringleiding" Or element3.Name = "Mat_spe_PE800" Then
      Set symbool = element3
        If symbool.HasAttributes Then
        attributen = symbool.GetAttributes
        For j = LBound(attributen) To UBound(attributen)
        Set attribuut = attributen(j)
          If attribuut.TagString = "RNU" And attribuut.textstring <> "" Then bb = attribuut.textstring 'REGELUNITNUMMER
            If bb = unitonder10 Then
              For k = LBound(attributen) To UBound(attributen)
              Set attribuut = attributen(k)
                'element3.Highlight (True)
                'If attribuut.TagString = "RNU" And attribuut.TextString <> "" Then attribuut.TextString = unitonder10 'REGELUNITNUMMER
                If attribuut.TagString = "PE" And attribuut.textstring <> "" Then attribuut.textstring = frmGroeptekst.ComboBox4 'TYPE BUIS
                If attribuut.TagString = "PE120" And attribuut.textstring <> "" Then attribuut.textstring = frmGroeptekst.TextBox1 '120 METER
                If attribuut.TagString = "PE90" And attribuut.textstring <> "" Then attribuut.textstring = frmGroeptekst.TextBox2  '90 METER
                If attribuut.TagString = "PE60" And attribuut.textstring <> "" Then attribuut.textstring = frmGroeptekst.TextBox3 '60 METER
                If attribuut.TagString = "LMETER" And attribuut.textstring <> "" Then attribuut.textstring = frmGroeptekst.TextBox27 'werkelijke meters totaal
                If attribuut.TagString = "REGELUNITTYPE" And attribuut.textstring <> "" Then attribuut.textstring = REGELTYPE 'TYPE REGELUNIT
                If attribuut.TagString = "BEVESTIGINGSTYPE" And attribuut.textstring <> "" Then attribuut.textstring = frmGroeptekst.ComboBox1  'BEVESTIGING
             Next k
             bb = ""
           End If
       Next j
       
        End If
      End If
      End If
  Next element3
  
 End If
 Update

If frmGroeptekst.OptionButton6 = True Then
aantal_groepen = (Val(frmGroeptekst.TextBox1)) + (Val(frmGroeptekst.TextBox2)) + (Val(frmGroeptekst.TextBox3)) + (Val(frmGroeptekst.TextBox17))
If (Val(frmGroeptekst.TextBox1)) = 0 Then frmGroeptekst.TextBox1 = "-"
If (Val(frmGroeptekst.TextBox2)) = 0 Then frmGroeptekst.TextBox2 = "-"
If (Val(frmGroeptekst.TextBox3)) = 0 Then frmGroeptekst.TextBox3 = "-"
If frmGroeptekst.ComboBox3.Enabled = False Then
REGELTYPE = frmGroeptekst.ComboBox2 & " " & aantal_groepen
Else
REGELTYPE = frmGroeptekst.ComboBox2 & " " & aantal_groepen & "/" & frmGroeptekst.ComboBox3
End If
If frmGroeptekst.OptionButton7 = True Or frmGroeptekst.OptionButton8 = True Then REGELTYPE = frmGroeptekst.ComboBox2

'ALUFLEX
unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

 Dim element4 As Object
For Each element4 In ThisDrawing.ModelSpace
      If element4.ObjectName = "AcDbBlockReference" Then
      If UCase(element4.Name) = "MAT_SPE_ALU" Or element4.Name = "Mat_spe_ALUringleiding" Then
      Set symbool = element4
        If symbool.HasAttributes Then
        attributen = symbool.GetAttributes
        For j = LBound(attributen) To UBound(attributen)
        Set attribuut = attributen(j)
        If attribuut.TagString = "RNU" And attribuut.textstring <> "" Then bb = attribuut.textstring 'REGELUNITNUMMER
            If bb = unitonder10 Then
              For k = LBound(attributen) To UBound(attributen)
              Set attribuut = attributen(k)
             'element4.Highlight (True)
             'If attribuut.TagString = "RNU" And attribuut.TextString <> "" Then attribuut.TextString = unitonder10 'REGELUNITNUMMER
             If attribuut.TagString = "ALU" And attribuut.textstring <> "" Then attribuut.textstring = frmGroeptekst.ComboBox4 'TYPE BUIS
             If attribuut.TagString = "ALU200" And attribuut.textstring <> "" Then attribuut.textstring = frmGroeptekst.TextBox1  '120 METER
             If attribuut.TagString = "ALU100" And attribuut.textstring <> "" Then attribuut.textstring = frmGroeptekst.TextBox2  '90 METER
             If attribuut.TagString = "ALU50" And attribuut.textstring <> "" Then attribuut.textstring = frmGroeptekst.TextBox3 '60 METER
             If attribuut.TagString = "REGELUNITTYPE" And attribuut.textstring <> "" Then attribuut.textstring = REGELTYPE 'TYPE REGELUNIT
             If attribuut.TagString = "BEVESTIGINGSTYPE" And attribuut.textstring <> "" Then attribuut.textstring = frmGroeptekst.ComboBox1  'BEVESTIGING
             If attribuut.TagString = "PEALU200" And OptionButton6 = True Then attribuut.textstring = "200 meter :" 'Aluflex 200 METER
             If attribuut.TagString = "PEALU100" And OptionButton6 = True Then attribuut.textstring = "100 meter :" 'Aluflex 100 METER
             If attribuut.TagString = "PEALU50" And OptionButton6 = True Then attribuut.textstring = " 50 meter :" 'Aluflex 100 METER
             Next k
             bb = ""
             End If
             
           Next j
       
        End If
      End If
      End If
  Next element4
 End If
  Update
  
  
'  Dim pb2(0 To 2) As Double
'  If OptionButton1.Value = True Then zakken = 210
'  If OptionButton2.Value = True Or OptionButton6.Value = True Then zakken = 179
'  If TextBox11 = "0" And TextBox25 <> "0" Then zakken = 179
'
'  pb2(0) = pb1(0) - (scaal * 460)
'  pb2(1) = pb1(1) + (scaal * zakken) '179) '177'210)
'  pb2(2) = pb1(2)
'
  'juiste regelunitblokje.dwg inserten in de tekening
  Dim bestand2 As String
  bestand2 = frmGroeptekst.ComboBox2 & ".dwg"
  If frmGroeptekst.ComboBox2 = "RUW-Groot" Then bestand2 = "RUW" & ".dwg"
  If frmGroeptekst.ComboBox2 = "RUW-Klein" Then bestand2 = "RUW" & ".dwg"
  If frmGroeptekst.ComboBox2 = "RUB-R" And aantal_groepen > 4 Then bestand2 = "RUH-R" & ".dwg"
  If frmGroeptekst.ComboBox2 = "RUB-RT" And aantal_groepen > 4 Then bestand2 = "RUH-RT" & ".dwg"
  If frmGroeptekst.ComboBox2 = "RUB-S" And aantal_groepen > 4 Then bestand2 = "RUH-S" & ".dwg"
  If frmGroeptekst.ComboBox2 = "VSKO" Then bestand2 = "VSKO-B" & ".dwg"
   Dim bestand3 As String
  bestand3 = "c:\acad2002\dwg\" & frmGroeptekst.ComboBox2 & ".txt"  'tekstbestand met afmetingen
  If frmGroeptekst.ComboBox2 = "VSKO" Then bestand3 = "c:\acad2002\dwg\" & frmGroeptekst.ComboBox2 & "-B.txt"  'tekstbestand met afmetingen
  
  Update
  'MsgBox bestand2 & " - " & bestand3

 Call unitblock(aantal_groepen, bestand2, bestand3, insp, scaal)
  
End Sub
Sub unitblock(aantal_groepen, bestand2, bestand3, insp, scaal)
'unitblok  ----------------
'unitblok  ----------------
'unitblok  ----------------
'unitblok  ----------------
 
 Set blockRefObj = ThisDrawing.ModelSpace.InsertBlock(insp, bestand2, scaal, scaal, 1, 0)
  Update
 
If frmGroeptekst.OptionButton7 = True Or frmGroeptekst.OptionButton8 = True Or frmGroeptekst.ComboBox2 = "RINGLEIDING" Then
 afmunitRING = "RINGLEIDING"
Else


 'open text bestand om afmetingen van de unit uit te lezen
  aantal_groepen2 = aantal_groepen
Const ForReading = 1, ForWriting = 2, ForAppending = 3
Const TristateUseDefault = -2, TristateTrue = -1, TristateFalse = 0
Dim fs, a, afmunit
Set fs = CreateObject("Scripting.FileSystemObject")
Set a = fs.OpenTextFile(bestand3, ForReading, False)
Do While aantal_groepen2 <> 0
    afmunit = a.ReadLine
    aantal_groepen2 = aantal_groepen2 - 1
Loop
a.Close 'sluiten van tekstbestand
End If
 

unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If


Dim element5 As Object
unit = frmGroeptekst.ComboBox2
If frmGroeptekst.ComboBox2 = "RUW-Groot" Then unit = "RUW"
If frmGroeptekst.ComboBox2 = "RUW-Klein" Then unit = "RUW"
If frmGroeptekst.ComboBox2 = "RUB-R" And aantal_groepen > 4 Then unit = "RUH-R"
If frmGroeptekst.ComboBox2 = "RUB-RT" And aantal_groepen > 4 Then unit = "RUH-RT"
If frmGroeptekst.ComboBox2 = "RUB-S" And aantal_groepen > 4 Then unit = "RUH-S"
If frmGroeptekst.ComboBox2 = "VSKO" Then unit = "VSKO-B"


For Each element5 In ThisDrawing.ModelSpace
      If element5.ObjectName = "AcDbBlockReference" Then
      If UCase(element5.Name) = unit Then
      Set symbool = element5
        If symbool.HasAttributes Then
        attributen = symbool.GetAttributes
        For I = LBound(attributen) To UBound(attributen)
        Set attribuut = attributen(I)
         If unit = "RINGLEIDING" Then
          If attribuut.TagString = "AFMETINGEN" And attribuut.textstring = "" Then attribuut.textstring = afmunitRING 'AFMETING VAN DEUNIT
          Else
          If attribuut.TagString = "AFMETINGEN" And attribuut.textstring = "" Then attribuut.textstring = afmunit 'AFMETING VAN DEUNIT
        End If
        If attribuut.TagString = "UNITNUMMER" And attribuut.textstring = "" Then attribuut.textstring = unitonder10 'UNITNUMMER
        Next I
       End If
      End If
      End If
 Next element5


  Call RESET
  'Unload frmGroeptekst
  'Unload Me
End Sub

Attribute VB_Name = "Waarschuwing"
Sub waarschuwing()
frmGroeptekst.TextBox2.BackColor = &HFFFF&
frmWaarschuwing.Show
End Sub

Attribute VB_Name = "Zoek_blok"
Sub zoek_blok()

unittel = frmGroeptekst.TextBox9

If unittel > 0 And unittel < 10 Then
  unitonder10 = "0" & frmGroeptekst.TextBox9
Else
  unitonder10 = frmGroeptekst.TextBox9
End If


For Each element In ThisDrawing.ModelSpace
      If element.ObjectName = "AcDbBlockReference" Then
      If element.Name = "Mat_spe_PE" Or element.Name = "Mat_spe_ZD" Or element.Name = "Mat_spe_ZD_1627" Or element.Name = "Mat_spe_ALU" Or _
      element.Name = "Mat_spe_PEringleiding" Or element.Name = "Mat_spe_ZDringleiding" Or _
      element.Name = "Mat_spe_ALUringleiding" Or element.Name = "Mat_spe_PE800" Or element.Name = "Mat_spe_FLEX" Then
      
      Set symbool = element
        If symbool.HasAttributes Then
        attributen = symbool.GetAttributes
        For I = LBound(attributen) To UBound(attributen)
        Set attribuut = attributen(I)
        If attribuut.TagString = "RNU" And attribuut.textstring <> "" Then bb = attribuut.textstring 'REGELUNITNUMMER
            If bb = unitonder10 Then
              For k = LBound(attributen) To UBound(attributen)
              Set attribuut = attributen(k)
       
                 If attribuut.TagString = "PE" Then
                 frmGroeptekst.OptionButton2.Value = True
                 frmGroeptekst.ComboBox4.Value = attribuut.textstring
                 frmGroeptekst.CheckBox8.Visible = True
                 End If
                 If attribuut.TagString = "PE" And Left(attribuut.textstring, 7) = "ALUFLEX" Then
                 frmGroeptekst.OptionButton6.Value = True
                 frmGroeptekst.ComboBox4.Value = attribuut.textstring
                 End If
                 If attribuut.TagString = "WTHZD" And attribuut.textstring = "WTH-ZD 16 * 2,7 mm" Then OptionButton9 = True
                 If attribuut.TagString = "WTHZD" And OptionButton1 = True Then frmGroeptekst.ComboBox4.Value = attribuut.textstring
                 If attribuut.TagString = "ALU" Then frmGroeptekst.ComboBox4.Value = attribuut.textstring
                 If attribuut.TagString = "BEVESTIGINGSTYPE" Then frmGroeptekst.ComboBox1.Value = attribuut.textstring
                 
                 If attribuut.TagString = "REGELUNITTYPE" Then
                   RT = attribuut.textstring
                 
                  If RT <> "RINGLEIDING" Then
                  trimstring = Split(RT, (" "))
                  Dim mystr As Variant
                  mystr = Len(trimstring(1))
                  frmGroeptekst.ComboBox2 = trimstring(0)
                         
                   If mystr > 2 Then
                   trimstring2 = Split(trimstring(1), ("/"))
                   ComboBox3 = trimstring2(1)
                   End If
                 
                  End If
                 If RT = "RINGLEIDING" Then frmGroeptekst.OptionButton7.Value = True
        
                 
                 End If
             Next k
             bb = ""
             End If
       Next I
       
        End If
      End If
      End If
  Next element


End Sub

Attribute VB_Name = "frmExportXLS"
Attribute VB_Base = "0{EE7FC1D6-E3B4-4392-9702-74E7A3F899CD}{B30F64BC-2A7C-4426-A1E5-BE8D1945CD82}"
Attribute VB_GlobalNameSpace = False
Attribute VB_Creatable = False
Attribute VB_PredeclaredId = True
Attribute VB_Exposed = False
Attribute VB_TemplateDerived = False
Attribute VB_Customizable = False

'26-01-2004 export werk lengte's naar xls-bestand
'M.Bosch en G.C.Haak
#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
frmExportXLS.Width = 285
frmExportXLS.Height = 88
On Error Resume Next

 'Kill ("c:\acad2002\layerlijst.txt")
Call exptek
End Sub
Sub exptek()

Call zoekblad(bladnummer)
TextBox14 = bladnummer

 If TextBox14 = "" Then
     Exit Sub
 End If


TextBox13 = Clear
For Each layerObj In ThisDrawing.Layers
     If Left(layerObj.Name, 5) = "groep" Then TextBox13 = (Val(TextBox13)) + 1  'aantal groepen
Next 'layerobj


For Each element2 In ThisDrawing.ModelSpace
      If element2.ObjectName = "AcDbBlockReference" Then
      If UCase(element2.Name) = "KADERLOGO" Or UCase(element2.Name) = "LOGOTGH" Then
      Set symbool = element2
        If symbool.HasAttributes Then
        attributen = symbool.GetAttributes
        For k = LBound(attributen) To UBound(attributen)
        Set attribuut = attributen(k)
        'If attribuut.TagString = "FORMAAT" Then FRMNO = attribuut.TextString
        If attribuut.TagString = "SCHAAL" Then schaalfaktor = attribuut.textstring
        Next k
       
      End If
      End If
      End If
      
Next element2

vartab = ThisDrawing.GetVariable("EXTMAX")

' A3 T/M A0+
If vartab(0) >= 2045 And vartab(0) <= 2055 Or vartab(0) >= 2915 And vartab(0) <= 2925 _
    Or vartab(0) >= 4175 And vartab(0) <= 4185 Or vartab(0) >= 5890 And vartab(0) <= 5900 _
    Or vartab(0) >= 7840 And vartab(0) <= 7850 Then
    maxwaarde = 1
Else
    maxwaarde = 2
End If
If vartab(0) >= 16715 And vartab(0) <= 16725 Or vartab(0) >= 23575 And vartab(0) <= 23585 _
    Or vartab(0) >= 31375 And vartab(0) <= 31385 Then
    maxwaarde = 4
End If
Update

If schaalfaktor = "1:50" And maxwaarde = 1 Then scaal = 1
If schaalfaktor = "1:100" And maxwaarde = 1 Then scaal = 2
If schaalfaktor = "1:200" And maxwaarde = 1 Then scaal = 4

If schaalfaktor = "1:50" And maxwaarde = 2 Then scaal = 0.5
If schaalfaktor = "1:100" And maxwaarde = 2 Then scaal = 1
If schaalfaktor = "1:200" And maxwaarde = 2 Then scaal = 2

If schaalfaktor = "1:200" And maxwaarde = 4 Then scaal = 1
TextBox19 = scaal


teknaam = ThisDrawing.GetVariable("dwgname")    'teknaam = ThisDrawing.GetVariable("dwgname")
TextBox16 = teknaam
TextBox17 = ThisDrawing.GetVariable("dwgprefix")  'pad = ThisDrawing.GetVariable("dwgprefix")
teknaam1 = Split(teknaam, ("."))                'teknaam1 = Split(teknaam, ("."))

         Dim mystr As Variant
         mystr = Len(teknaam)
         over = mystr - 4 'aantal karakters
         teknaam6 = Left(teknaam, over)

'TextBox18 = teknaam1(0)
TextBox18 = teknaam6


'aantal groepen groter dan 30 ????
If TextBox13 > 30 Then
frmExportXLS.Hide


'bestandnaam2 = pad & teknaam1(0) & "-export" & ".dwg"
bestandnaam2 = TextBox17 & TextBox18 & "-export" & ".dwg"
TextBox20 = bestandnaam2

'Kill (bestandnaam)
'Call zoekblad(bladnummer)

ThisDrawing.SendCommand "-layer" & vbCr & "unlock" & vbCr & "*" & vbCr & vbCr
ThisDrawing.SendCommand "-layer" & vbCr & "set" & vbCr & "0" & vbCr & vbCr
ThisDrawing.SendCommand "-layer" & vbCr & "Freeze" & vbCr & "*" & vbCr & vbCr
ThisDrawing.SendCommand "-layer" & vbCr & "Thaw" & vbCr & "groep*" & vbCr & vbCr
ThisDrawing.SendCommand "-layer" & vbCr & "Thaw" & vbCr & "gt" & vbCr & vbCr

ThisDrawing.SendCommand "_copyclip" & vbCr & "all" & vbCr & vbCr


ThisDrawing.SendCommand "-layer" & vbCr & "Thaw" & vbCr & "*" & vbCr & vbCr


templatenaam = ThisDrawing.GetVariable("acadver")
If templatenaam = "15.06s (LMS Tech)" Then ThisDrawing.Application.Documents.Add ("acad2000.dwt")
'If templatenaam = "16.0s (LMS Tech)" Then ThisDrawing.Application.Documents.Add ("acad2004.dwt")
If templatenaam >= "16.0s (LMS Tech)" Then ThisDrawing.Application.Documents.Add ("acad2004.dwt")

ThisDrawing.SendCommand "_pasteclip" & vbCr & "0,0" & vbCr

ThisDrawing.SaveAs (bestandnaam2)
'frmExportXLS.Show
End If

End Sub
Sub zoekblad(bladnummer)
For Each element2 In ThisDrawing.ModelSpace
      If element2.ObjectName = "AcDbBlockReference" Then
      If UCase(element2.Name) = "KADERLOGO" Or UCase(element2.Name) = "LOGOTGH" Then
      Set symbool = element2
        If symbool.HasAttributes Then
        attributen = symbool.GetAttributes
        For I = LBound(attributen) To UBound(attributen)
        Set attribuut = attributen(I)
        If attribuut.TagString = "BLAD" Then bladnummer = attribuut.textstring
        Next I
       
      End If
      End If
      End If
  Next element2
 Update
End Sub
Private Sub CommandButton2_Click()
'voorbeeld groep 1.01 = 17.51 meter. --> wordt een rol van 40 meter
'waar je op scheidt valt weg
'trimst(0)-> groep 1.01
'trimst(1) -> 17.51 meter. --> wordt een rol van 40 meter
'cmdAfsluiten.Enabled = False
If TextBox14 = "" Then
   MsgBox "Één van de onderstaande fouten is geconstateerd:" & Chr(13) & Chr(10) & "1 - Het kaderlogo is niet aanwezig in de tekening," & Chr(13) & "2 - Of het bladnummer is niet ingevuld," & Chr(13) & "3 - Of er zijn 2 Kaderlogo's aanwezig.", vbExclamation, "Foutmelding"
   Unload Me
   Exit Sub
End If
 

ListBox1.Clear
ListBox3.Clear
TextBox12 = ""

Call cmdLayers_Click

'teknaam = TextBox16
'pad = ThisDrawing.GetVariable("dwgprefix")
teknaam1 = TextBox18
'Split(teknaam, ("."))

bestandnaam = TextBox17 & TextBox18 & "-lh" & ".xls"
'teknaam1 (0) & "-lh" & ".xls"


unitstrim1 = 1
 
teller = ListBox1.ListCount
For I = 0 To teller - 1
   'Define the text object
    textstring = ListBox1.List(I)
    trimst = Split(textstring, ("=")) 'groepsnaam en de rest scheiden
    trimst1 = Split(trimst(0), (" "))
    trimst2 = Split(trimst(1), (" "))
    
       
    unitstrim2 = Split(trimst1(1), ("."))
    If (unitstrim2(0) > unitstrim1) Then
      trimst3 = " - "
      ListBox3.AddItem (trimst3)
    End If
    
    trimst3 = "[" & TextBox14 & "] " & trimst(0) & "-" & (trimst2(1))
'bladnummer
    ListBox3.AddItem (trimst3) 'groepsnaam invullen
    unitstrim1 = unitstrim2(0)
Next I

Const ForReading = 1, ForWriting = 2, ForAppending = 8
Dim fs, f
Dim s1 As AcadSelectionSet
Set fs = CreateObject("Scripting.FileSystemObject")
Set f = fs.OpenTextFile(bestandnaam, ForWriting, -2)
f.Close

teller = ListBox3.ListCount
For I = 0 To teller - 1
   'Define the text object
    xtstring = ListBox3.List(I)
    xtstring2 = Split(xtstring, ("-"))
    Set f = fs.OpenTextFile(bestandnaam, ForAppending, -2) '.xls"
    f.write xtstring2(0)
    f.write Chr(9)
    f.write xtstring2(1)
    'f.write Chr(9)
    'f.write xtstring2(2)
    f.write Chr(13) + Chr(10)
    f.Close
Next I


If TextBox13 > 30 Then ThisDrawing.Close
 If TextBox13 > 30 Then
  bestandnaam3 = TextBox17 & TextBox18 & "-export" & ".dwg"
  Kill (bestandnaam3)
 End If
Unload Me
End Sub
Sub cmdLayers_Click()

ListBox1.Clear
Update
On Error Resume Next
  
 Dim cirkel As Object
 Dim element As Object
 Dim Lengte As Double
 Dim laagobj As Object
 
 Dim minaantal As Integer
 Dim maxaantal As Integer
 Dim I As Integer
 I = 0
 minaantal = 0
 maxaantal = ThisDrawing.Layers.Count
 For Each laagobj In ThisDrawing.Layers
 I = I + 1
 ProgressBar1.Min = minaantal
 ProgressBar1.Max = maxaantal
 ProgressBar1.Value = I
 
      mystr = Left(laagobj.Name, 5)
      If mystr = "GROEP" Then mystr = "groep"
      If mystr = "groep" Then
        For Each element In ThisDrawing.ModelSpace
          If element.Layer = laagobj.Name Then
                'BEREKENEN TOTALE LENGTE
                If element.EntityName = "AcDbLine" Then Lengte = Lengte + element.Length
                If element.EntityName = "AcDbArc" Then Lengte = Lengte + element.ArcLength
             End If 'elementlayer
             Next element
             
              For Each cirkel In ThisDrawing.ModelSpace
                If cirkel.Layer = laagobj.Name Then
                If cirkel.EntityName = "AcDbCircle" Then
                
                
                For Each element In ThisDrawing.ModelSpace
                    If element.ObjectName = "AcDbBlockReference" Then
                    If UCase(element.Name) = "GROEPTEKSTBLOKNEW" Then
                    Set symbool = element
                    If symbool.HasAttributes Then
                     attributen = symbool.GetAttributes
                     For I = LBound(attributen) To UBound(attributen)
                         Set attribuut = attributen(I)
                         If attribuut.TagString = "GROEPTEKST" Then gpt = attribuut.textstring
                         If gpt = laagobj.Name Then
                          If attribuut.TagString = "WANDHOOGTE" Then wdh = attribuut.textstring
                         End If 'gpt
                         Next I
                        End If
                      End If
                   End If
                 Next element
                      
                wdh1 = Split(wdh, " ")
                z = z + 1
                 zlengte = (z * (wdh1(0) * 100)) + 100
                wvaanwezig = " (WV)"
                
                End If
                End If
              Next cirkel
               
              '  zlengte = zlengte - Lengte
        '  End If '2e mystr
                
    Lengte = (Lengte * TextBox19) + zlengte
    Lengte = Lengte / 100
    'Lengte = Lengte * scaal
    Lengte = Round(Lengte, 0)
    totalrollen = totalrollen + Lengte
 
    If mystr = "groep" Then
    s = " = "
    Else
    s = "  = "
    End If
    
    
    zw = Len(laagobj.Name)
    
    If zw > 9 And (mystr = "groep" Or mystr = "GROEP") Then
    
    D = laagobj.Name & s & Lengte & " meter. "
    D = D & " " & wvaanwezig
    ListBox1.AddItem (D)
    End If
    'End If
    
     
    Lengte = 0 'Lengte leeggooien voordat de volgende groep wordt gemeten
    zlengte = 0
    z = 0
    wvaanwezig = ""
  End If  'end if  mystr
 Next laagobj
 ProgressBar1.Value = minaantal
 'Update
  

   'lijst rangschikken
  Dim Veld(0 To 500)
  Dim textstring2 As String
  
    For I = 0 To ListBox1.ListCount - 1
    textstring2 = ListBox1.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox1.Clear
 
  For x = 0 To UBound(Veld)
  If Veld(x) <> "" Then ListBox1.AddItem Veld(x)
  Next x
 TextBox12 = totalrollen
 
 End Sub

Private Sub cmdAfsluiten_Click()
'checkopexport = Right(TextBox20, 5)
If TextBox20 <> "" Then
 checkopexport = Split(TextBox20, ".")
 checkopexport1 = Right(checkopexport(0), 6)
 If checkopexport1 = "export" Then ThisDrawing.Close
 bestandnaam3 = TextBox17 & TextBox18 & "-export" & ".dwg"
 Kill (bestandnaam3)
End If

Unload Me
End Sub

Attribute VB_Name = "frmExtraopties"
Attribute VB_Base = "0{C9BDD02A-50D2-4A1F-8084-B5058FDE92C0}{C3D3CF2B-1DB3-4939-8182-8C1BDC6BA4AE}"
Attribute VB_GlobalNameSpace = False
Attribute VB_Creatable = False
Attribute VB_PredeclaredId = True
Attribute VB_Exposed = False
Attribute VB_TemplateDerived = False
Attribute VB_Customizable = False
'23-2-2005 Extra Opties
'4-7-2005 wijziging
'M.Bosch en G.C.Haak

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If


frmExtraopties.TextBox2.Value = 1
frmExtraopties.TextBox3.SetFocus
End Sub
Private Sub CommandButton1_Click()
On Error Resume Next
z1 = (Val(frmExtraopties.TextBox2))
z2 = (Val(frmExtraopties.TextBox3))

If z2 < z1 Then
  MsgBox "De laatste waarde moet groter zijn dan de 1e....!!!!", vbExclamation, "Let op"
  Exit Sub
End If

cc = frmExtraopties.TextBox1 & "_" & frmExtraopties.TextBox2
If (Val(frmExtraopties.TextBox2)) > 0 And (Val(frmExtraopties.TextBox2)) < 10 Then cc = frmExtraopties.TextBox1 & "_" & "0" & frmExtraopties.TextBox2

bb = (Val(frmExtraopties.TextBox2))

For I = (Val(frmExtraopties.TextBox2)) To (Val(frmExtraopties.TextBox3))
 
 C = frmExtraopties.TextBox1 & "_" & I

 If I > 0 And I < 10 Then C = frmExtraopties.TextBox1 & "_" & "0" & I
 
 Set newLayer = ThisDrawing.Layers.Add(C)
 ThisDrawing.ActiveLayer = newLayer


        rr = ThisDrawing.ActiveLayer.TrueColor.ColorIndex  '
        'MsgBox C & " -" & rr
        
        If rr = 2 Or rr = 7 Then
        
        Dim col As New AcadAcCmColor
        col.ColorMethod = AutoCAD.acColorMethodForeground

        Dim layColor As New AcadAcCmColor
        'Set layColor = AcadApplication.GetInterfaceObject("AutoCAD.AcCmColor.16")
        Call layColor.SetRGB(255, 255, 0)

        ThisDrawing.ActiveLayer.TrueColor = layColor
        End If
        
        
 Next I

frmExtraopties.TextBox2 = bb
Set newLayer = ThisDrawing.Layers.Add(cc)
ThisDrawing.ActiveLayer = newLayer
Unload Me
End Sub
Private Sub TextBox2_Change()
Dim b As Double
On Error Resume Next
b = frmExtraopties.TextBox2.Text

If Err Then
   frmExtraopties.TextBox2 = Clear
   PlaatsButton.Enabled = False
  Exit Sub
  End If
  
If b > -1 And b < 1 Then
    frmExtraopties.TextBox2 = Clear
    frmExtraopties.TextBox2.SetFocus
End If
End Sub

Private Sub TextBox3_Change()
Dim a As Double
On Error Resume Next
a = frmExtraopties.TextBox3.Text

If Err Then
   frmExtraopties.TextBox3 = Clear
   PlaatsButton.Enabled = False
  Exit Sub
  End If
  
If a > -1 And a < 1 Then
    frmExtraopties.TextBox3 = Clear
    frmExtraopties.TextBox3.SetFocus
End If
End Sub
Private Sub cmdAfsluiten_Click()
Unload Me
End Sub

Attribute VB_Name = "frmFlexfixafstand"
Attribute VB_Base = "0{8CB256F9-7F59-4247-9542-594151C1C874}{2631A059-89ED-480C-BB93-1255505C7619}"
Attribute VB_GlobalNameSpace = False
Attribute VB_Creatable = False
Attribute VB_PredeclaredId = True
Attribute VB_Exposed = False
Attribute VB_TemplateDerived = False
Attribute VB_Customizable = False
'13-09-2005 Flexfixafstand
'M.Bosch en G.C.Haak


#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
End Sub
Private Sub cmdAfsluiten_Click()
Unload Me
If OptionButton1.Value = True Then ThisDrawing.SetVariable "filletrad", 10
If OptionButton2.Value = True Then ThisDrawing.SetVariable "filletrad", 12.5
If OptionButton3.Value = True Then ThisDrawing.SetVariable "filletrad", 15
If OptionButton4.Value = True Then ThisDrawing.SetVariable "filletrad", 20
If OptionButton5.Value = True Then ThisDrawing.SetVariable "filletrad", 25
If OptionButton6.Value = True Then ThisDrawing.SetVariable "filletrad", 30
End Sub

Attribute VB_Name = "frmGroeptekst"
Attribute VB_Base = "0{EA51DC31-F61B-4A4A-B15D-371CCEA5159E}{76A7116A-0C0A-492B-BCC6-819CA5577092}"
Attribute VB_GlobalNameSpace = False
Attribute VB_Creatable = False
Attribute VB_PredeclaredId = True
Attribute VB_Exposed = False
Attribute VB_TemplateDerived = False
Attribute VB_Customizable = False
'17-12-2002 Meten van groepen
'M.Bosch en G.C.Haak
'kruisje uitschakelen
'BESTANDEN: groeptekstbloknew.DWG
'Mat_spe_zd.dwg | Mat_spe_pe.dwg | Mat_spe_flex.dwg |
'TXT en DWG - Herz|Ruh-r|Ruh-N|ruh-rt|rub-r|rub-rt|rubk-r|rubk-rt|LT|lt-s|lt-n
'TXT en DWG - RUW|ruw-klein.txt|ruw-groot.txt|ruv|ruh-s|rub-s|kmv

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000

Private Sub ListBox3_Click()

End Sub

Private Sub TextBox28_Change()
Dim b As Double
On Error Resume Next
TextBox28.SetFocus
b = TextBox28.Text
If Err Then
   TextBox28 = "0"
Exit Sub
End If
End Sub

Private Sub TextBox30_Change()
If OptionButton9.Value = True And CheckBox2.Value = True Then texbox11 = TextBox30
End Sub

Private Sub ToggleButton2_Click()
If ToggleButton2.Value = False Then
   ToggleButton2.Picture = LoadPicture("c:\acad2002\dwg\engeland.bmp")
   ToggleButton2.ControlTipText = "Omschakelen naar engels"
   Call togglemodule.groeptekst_dutch
   Call combolijst1 'combobox1 vullen
   End If
If ToggleButton2.Value = True Then
   ToggleButton2.Picture = LoadPicture("c:\acad2002\dwg\nederland.bmp")
   ToggleButton2.ControlTipText = "Switch to Dutch"
   Call togglemodule.groeptekst_english
   If frmGroeptekst.OptionButton10.Value = True Then Call togglemodule.groeptekst_combolijst5 'combobox1 vullen
   End If
End Sub

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
  
  frmGroeptekst.CheckBox8.Visible = False

Call combolijst1 'combobox1 vullen
Call Combolijst2 'combobox2 vullen
Call Combolijst3 'combobox3 vullen
Call combolijst4 'combobox4 vullen
Call leidingtype
Call LEIDINGSOORT
Call wklengte

frmGroeptekst.Height = 400
frmGroeptekst.Width = 455
TextBox23 = ThisDrawing.GetVariable("userr4")
ThisDrawing.SendCommand "-layer" & vbCr & "U" & vbCr & "gt" & vbCr & "ON" & vbCr & "gt" & vbCr & "T" & vbCr & "gt" & vbCr & vbCr
Label33 = 0
TextBox9.SetFocus
Label11.Caption = Clear 'wordt gevuld en uitgelezen met groepsnummer

Dim newLayer As AcadLayer
Set newLayer = ThisDrawing.Layers.Add("GT")
ThisDrawing.ActiveLayer = newLayer


End Sub
Private Sub CheckBox2_Click()
If CheckBox2.Value = True Then
     CheckBox6.Enabled = False
     CheckBox7.Enabled = False
End If
If CheckBox2.Value = False Then
     CheckBox6.Enabled = True
     CheckBox7.Enabled = True
End If

End Sub

Private Sub CheckBox6_Click()
If CheckBox6.Value = True Then CheckBox2.Enabled = False
If CheckBox6.Value = False Then CheckBox2.Enabled = True
End Sub

Private Sub CheckBox7_Click()
If CheckBox7 = True Then TextBox24.Visible = True
If CheckBox7 = False Then TextBox24.Visible = False
End Sub

Private Sub ComboBox1_Change()
If ComboBox1 = "IFD-Polystyreen" Then ComboBox4 = "PE-RT 14*2 mm"
End Sub


Private Sub CheckBox1_Click()
If CheckBox1.Value = True Then
 If OptionButton1.Value = True Then
   Label25.Caption = "WTHZD"
   Else
   Label25.Caption = "PE"
 End If
'OptionButton1.Enabled = False
'OptionButton2.Enabled = False
TextBox14.Visible = True: Label24.Visible = True: TextBox1.Visible = False
TextBox2.Visible = False: TextBox3.Visible = False: TextBox4.Visible = False
TextBox5.Visible = False: TextBox6.Visible = False: TextBox7.Visible = False
TextBox15.Visible = False: TextBox16.Visible = False
Label2.Visible = False: Label3.Visible = False: Label4.Visible = False
Label5.Visible = False: Label6.Visible = False: Label7.Visible = False
Label27.Visible = False: Label28.Visible = False
Label1.Caption = Clear
TextBox14.SetFocus
TextBox14 = Clear
End If

If CheckBox1.Value = False Then
'OptionButton1.Enabled = True: OptionButton2.Enabled = True
TextBox14.Visible = False: Label24.Visible = False
Label25.Caption = Clear
Call RESET
End If
End Sub
Private Sub OptionButton7_Click()
If frmGroeptekst.OptionButton7 = True Then
     cmdTelrollen.Enabled = True
     ComboBox2 = "RINGLEIDING"
     End If
End Sub
Private Sub OptionButton8_Click()
If frmGroeptekst.OptionButton8 = True Then
     cmdTelrollen.Enabled = True
     ComboBox2 = "RINGLEIDING"
     End If
End Sub
Private Sub commandbutton4_click()
Call Checklayer2.Checklayer2
End Sub
Private Sub commandbutton6_click()
Call Update_module.update_unitlogo
Unload Me
End Sub
Private Sub OptionButton5_Click()
If OptionButton5.Value = True Then TextBox13.Visible = True
End Sub
Private Sub TextBox14_Change()
Label1.Caption = TextBox14 & " meter"
TextBox1.Visible = True
Dim TA As Double
On Error Resume Next
TextBox14.SetFocus
TA = TextBox14.Text
If Err Then
   TextBox14 = Clear
  Exit Sub
  End If
End Sub
Private Sub ToggleButton1_Click()
If ToggleButton1.Value = False Then
   ToggleButton1.ForeColor = RGB(0, 0, 0)
   ToggleButton1.Caption = "2,5 meter"
   End If
If ToggleButton1.Value = True Then
   ToggleButton1.ForeColor = RGB(255, 0, 0)
   ToggleButton1.Caption = "2 meter"
   OptionButton5.Value = False: TextBox13.Visible = False
End If
End Sub
Sub leidingtype()
Dim element As Object
Dim layerObj As AcadLayer

For Each element In ThisDrawing.ModelSpace
      If element.ObjectName = "AcDbBlockReference" Then
      If element.Name = "Mat_spe_PE" Or element.Name = "Mat_spe_ZD" Or element.Name = "Mat_spe_ALU" Or _
      element.Name = "Mat_spe_PEringleiding" Or element.Name = "Mat_spe_ZDringleiding" Or _
      element.Name = "Mat_spe_ALUringleiding" Or element.Name = "Mat_spe_PE800" _
      Or element.Name = "Mat_spe_FLEX" Or element.Name = "Mat_spe_ZD_1627" Or element.Name = "Mat_spe_ZD_1627500" Then
      
      Set symbool = element
        If symbool.HasAttributes Then
        attributen = symbool.GetAttributes
        For I = LBound(attributen) To UBound(attributen)
        Set attribuut = attributen(I)
       
         If attribuut.TagString = "PE" Then
         OptionButton2.Value = True
         ComboBox4.Value = attribuut.textstring
         CheckBox8.Visible = True
         End If
         If attribuut.TagString = "PE" And Left(attribuut.textstring, 7) = "ALUFLEX" Then
         OptionButton6.Value = True
         ComboBox4.Value = attribuut.textstring
         End If
         If attribuut.TagString = "WTHZD" And (attribuut.textstring = "WTH-ZD 16 * 2,7 mm" Or attribuut.textstring = "WTH-ZD 16*2,7 mm") Then OptionButton9 = True
         If attribuut.TagString = "PE" And (attribuut.textstring = "WTH-ZD 16 * 2,7 mm" Or attribuut.textstring = "WTH-ZD 16*2,7 mm") Then OptionButton9 = True
         If attribuut.TagString = "WTHZD" And OptionButton1 = True Then ComboBox4.Value = attribuut.textstring
         If attribuut.TagString = "ALU" Then ComboBox4.Value = attribuut.textstring
         If attribuut.TagString = "BEVESTIGINGSTYPE" Then ComboBox1.Value = attribuut.textstring
         If attribuut.TagString = "LMETER" Then CheckBox8.Value = True
         
         If attribuut.TagString = "REGELUNITTYPE" Then
           RT = attribuut.textstring
         
          If RT <> "RINGLEIDING" Then
          trimstring = Split(RT, (" "))
          Dim mystr As Variant
          mystr = Len(trimstring(1))
          ComboBox2 = trimstring(0)
                 
           If mystr > 2 Then
           trimstring2 = Split(trimstring(1), ("/"))
           ComboBox3 = trimstring2(1)
           End If
         
          End If
         'If RT = "RINGLEIDING" Then OptionButton7.Value = True

         
       End If
         
       Next I
       
        End If
      End If
      End If
  Next element
End Sub
Sub LEIDINGSOORT()
 For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                         Set attribuut = attributen(I)
                         If attribuut.TagString = "RINGLEIDING" Then RML = attribuut.textstring
                         If attribuut.TagString = "LEIDINGSOORT" Then WSL = attribuut.textstring
''''''                         If attribuut.TagString = "UNITNUMMER" Then UNITSjek = attribuut.textstring
                    Next I
                End If
            End If
        End If
    Next element
        
'If RML = "RM" Then frmGroeptekst.OptionButton7 = True
If RML = "RZ" Then frmGroeptekst.OptionButton8 = True
If WSL = "WTH-ZD 20*3,4 mm" Then frmGroeptekst.OptionButton1 = True
If WSL = "WTH-ZD 16*2,7 mm" Then frmGroeptekst.OptionButton9 = True

If WSL = "PE-RT 14*2 mm" Then
    frmGroeptekst.OptionButton2 = True
    frmGroeptekst.ComboBox4.ListIndex = 0
End If
If WSL = "PE-RT 16*2 mm" Then
    frmGroeptekst.OptionButton2 = True
    frmGroeptekst.ComboBox4.ListIndex = 1
End If
If WSL = "PE-RT 10*1,25 mm" Then
    frmGroeptekst.OptionButton2 = True
    frmGroeptekst.ComboBox4.ListIndex = 6
End If

If WSL = "ALUFLEX 14*2 mm" Then
    frmGroeptekst.OptionButton6 = True
    frmGroeptekst.ComboBox4.ListIndex = 0
End If
If WSL = "ALUFLEX 16*2 mm" Then
    frmGroeptekst.OptionButton6 = True
    frmGroeptekst.ComboBox4.ListIndex = 1
End If
If WSL = "ALUFLEX 18*2 mm" Then
    frmGroeptekst.OptionButton6 = True
    frmGroeptekst.ComboBox4.ListIndex = 2
End If
If WSL = "ALUFLEX 18*2 mm" Then
    frmGroeptekst.OptionButton6 = True
    frmGroeptekst.ComboBox4.ListIndex = 3
End If

'''UNITSJEK1 = Len(UNITSjek)
'''If UNITSJEK1 = 1 Then frmGroeptekst.CheckBox3.Value = True
End Sub
Sub wklengte()
Dim element As Object
For Each element In ThisDrawing.ModelSpace
      If element.ObjectName = "AcDbBlockReference" Then
      If element.Name = "groeptekstbloknew" Or element.Name = "GROEPTEKSTBLOKNEW" Then
      Set symbool = element
        If symbool.HasAttributes Then
        attributen = symbool.GetAttributes
        For I = LBound(attributen) To UBound(attributen)
        Set attribuut = attributen(I)
            If attribuut.TagString = "WERKLENGTE" And attribuut.textstring = "ja" Then frmGroeptekst.CheckBox2.Value = True
            If attribuut.TagString = "FLEXFIX" And attribuut.textstring = "ja" Then frmGroeptekst.CheckBox6.Value = True
        Next I
End If
End If
End If
Next element
End Sub
Private Sub cmdAfsluiten_Click()
Unload Me
End Sub
Private Sub CmdErase_Click()
On Error Resume Next
TextBox23 = 1
ThisDrawing.SetVariable "lispinit", 0
ThisDrawing.SetVariable "userr4", 1



If TextBox12 = "" Then
  MsgBox "Eerst unitnummer hieronder invullen.!!!!", vbExclamation, "Let op"
  TextBox12.SetFocus
End If


unittel = frmGroeptekst.TextBox12
If unittel > 0 And unittel < 10 Then
   frmGroeptekst.TextBox12 = "0" & frmGroeptekst.TextBox12
End If



Call delwand

Dim element As Object
Dim layerObj As AcadLayer
'groeptekstbloknew verwijderen
For Each element In ThisDrawing.ModelSpace
      If element.ObjectName = "AcDbBlockReference" Then
      If element.Name = "groeptekstbloknew" Or element.Name = "GROEPTEKSTBLOKNEW" Then
      Set symbool = element
        If symbool.HasAttributes Then
        attributen = symbool.GetAttributes
        For I = LBound(attributen) To UBound(attributen)
        Set attribuut = attributen(I)
               'groepen tijdelijk hernummeren
               If attribuut.TagString = "UNITNUMMER" Then unitnum = attribuut.textstring
               If attribuut.TagString = "GROEPTEKST" Then grpt = attribuut.textstring
                                           
               If unitnum = TextBox12 Or unitnum = unittel Then
               hernummer1 = grpt
               hernummer2 = hernummer1 & "h"
                 For Each layerObj In ThisDrawing.Layers
                    If layerObj.Name = hernummer1 Then layerObj.Name = hernummer2
                 Next 'layerobj
               End If
               
               If CheckBox6.Value = True Then  'flexfix
                If unitnum = TextBox12 Or unitnum = unittel Then
                
                hernummer3 = grpt & "_Flexfix_aanvoer"
                hernummer4 = hernummer3 & "h"
                hernummer5 = grpt & "_Flexfix_retour"
                hernummer6 = hernummer5 & "h"
                hernummer7 = grpt & "_Flexfix"
                hernummer8 = hernummer7 & "h"
                
                 For Each layerObj In ThisDrawing.Layers
                    If layerObj.Name = hernummer3 Then layerObj.Name = hernummer4
                    If layerObj.Name = hernummer5 Then layerObj.Name = hernummer6
                    If layerObj.Name = hernummer7 Then layerObj.Name = hernummer8
                 Next 'layerobj
                End If
               End If
          If unitnum = TextBox12 Or unitnum = unittel Then element.Erase
       Next I
       
        End If
      End If
      End If
       unitnum = 0
       grpt = 0

  Next element
  


Call layzondertekst 'uitgezet op 29-11  niet meer nodig

  
  'Mat_spe_zd en Mat_spe_pe en Mat_spe_ALU verwijderen
  For Each element In ThisDrawing.ModelSpace
      If element.ObjectName = "AcDbBlockReference" Then
      If element.Name = "Mat_spe_ZD" Or element.Name = "Mat_spe_PE" Or element.Name = "Mat_spe_PE800" _
      Or element.Name = "Mat_spe_ALU" Or element.Name = "Mat_spe_ZDringleiding" Or element.Name = "Mat_spe_PEringleiding" Or _
      element.Name = "Mat_spe_ALUringleiding" Or element.Name = "Mat_spe_FLEX" Or element.Name = "Mat_spe_ZD_1627" Or _
      element.Name = "Mat_spe_FLEX_Aankoppel" Or element.Name = "Mat_spe_ZD_1627500" Then
      Set symbool = element
        If symbool.HasAttributes Then
        attributen = symbool.GetAttributes
        For I = LBound(attributen) To UBound(attributen)
        Set attribuut = attributen(I)
        If attribuut.TagString = "RNU" Or attribuut.TagString = "rnu" Then
           If attribuut.textstring = TextBox12 Or attribuut.textstring = unittel Then
               element.Erase
            End If 'TEXTBOX 12
        End If 'if unitnummer
       Next I
       
        End If
      End If
      End If
  Next element
  Update
  
  'REGELUNITBLOKJE VERWIJDEREN
   For Each element In ThisDrawing.ModelSpace
      If element.ObjectName = "AcDbBlockReference" Then
If element.Name = "HERZ" Or element.Name = "RUH-R" Or element.Name = "RUH-RT" _
Or element.Name = "RUB-R" Or element.Name = "RUB-RT" Or element.Name = "RUBK-R" Or element.Name = "LT-VK" _
Or element.Name = "RUBK-RT" Or element.Name = "LT" Or element.Name = "LTS" Or element.Name = "LT-N" Or element.Name = "LTS-N" _
Or element.Name = "RUW" Or element.Name = "RUV" Or element.Name = "RUH-S" Or element.Name = "VSKO-B" _
Or element.Name = "RUB-S" Or element.Name = "KMV" Or element.Name = "RUH-N" Or element.Name = "RU-WW" Or element.Name = "RINGLEIDING" _
Or element.Name = "RU-WWN" Or element.Name = "RU-WWS" Or element.Name = "RU-WKN" Or element.Name = "RU-WKS" Then
      Set symbool = element
        If symbool.HasAttributes Then
        attributen = symbool.GetAttributes
        For I = LBound(attributen) To UBound(attributen)
        Set attribuut = attributen(I)
        If attribuut.TagString = "UNITNUMMER" Then
           If attribuut.textstring = TextBox12 Or attribuut.textstring = unittel Then
               element.Erase
            End If 'TEXTBOX 12
        End If 'if unitnummer
       Next I
      End If
     End If
     End If
   Next element
 Update
'EINDE REGELUNITBLOKJE VERWIJDEREN
  TextBox12 = Clear

End Sub
Private Sub CommandButton5_Click()
TextBox23 = 1
ThisDrawing.SetVariable "lispinit", 0
ThisDrawing.SetVariable "userr4", 1



If frmGroeptekst.CheckBox3.Value = False Then
    If TextBox18 > 0 And TextBox18 < 10 Then
       frmGroeptekst.TextBox18 = "0" & frmGroeptekst.TextBox18
    End If
End If

TextBox21 = TextBox19 - 1
TextBox22 = TextBox20

If TextBox19 > 0 And TextBox19 < 10 Then
   frmGroeptekst.TextBox19 = "0" & frmGroeptekst.TextBox19
End If


SAMENV = "groep " & TextBox18 & "." & TextBox19
ListBox2.AddItem (SAMENV)

Do Until TextBox21 = TextBox22
 TextBox21 = TextBox21 + 1
  If TextBox21 > 0 And TextBox21 < 10 Then samenv2 = "groep " & TextBox18 & "." & "0" & TextBox21
  'MsgBox SAMENV
  If TextBox21 > 9 Then samenv2 = "groep " & TextBox18 & "." & TextBox21
  ListBox2.AddItem (samenv2)
Loop

Dim element As Object
Dim layerObj As AcadLayer
'groeptekstbloknew verwijderen
  For Each element In ThisDrawing.ModelSpace
      If element.ObjectName = "AcDbBlockReference" Then
      If element.Name = "groeptekstbloknew" Or element.Name = "GROEPTEKSTBLOKNEW" Then
      Set symbool = element
        If symbool.HasAttributes Then
         attributen = symbool.GetAttributes
        
tellerj = ListBox2.ListCount
For j = 0 To tellerj - 1
  uitlees = ListBox2.List(j)
        
        For I = LBound(attributen) To UBound(attributen)
        Set attribuut = attributen(I)
               'groepen tijdelijk hernummeren
                If attribuut.TagString = "UNITNUMMER" Then unitnum = attribuut.textstring
                If attribuut.TagString = "GROEPTEKST" Then grpt = attribuut.textstring
            
                If unitnum = TextBox18 And uitlees = grpt Then element.Erase
                'MsgBox uitlees & " - " & grpt
                uitlees = 0
        Next I
Next j
       
         End If
      End If
      End If
       unitnum = 0
       grpt = 0
  Next element

 Update


tellerz = ListBox2.ListCount
For z = 0 To tellerz - 1
   'Define the text object
     If CheckBox6.Value = False Then
     hernaam = ListBox2.List(z)
     hernaam2 = hernaam & "h"
        For Each layerObj In ThisDrawing.Layers
         If layerObj.Name = hernaam Then layerObj.Name = hernaam2
        Next 'layerobj
     End If
    
    If CheckBox6.Value = True Then
        hernaam3 = ListBox2.List(z)
        hernaam4 = hernaam3 & "_Flexfix"
        hernaam5 = hernaam3 & "_Flexfix_aanvoer"
        hernaam6 = hernaam3 & "_Flexfix_retour"
     For Each layerObj In ThisDrawing.Layers
        If layerObj.Name = hernaam Then layerObj.Name = hernaam2
        If layerObj.Name = hernaam4 Then layerObj.Name = hernaam4 & "h"
        If layerObj.Name = hernaam5 Then layerObj.Name = hernaam5 & "h"
        If layerObj.Name = hernaam6 Then layerObj.Name = hernaam6 & "h"
     Next 'layerobj
    End If
Next z

TextBox18 = Clear: TextBox19 = Clear: TextBox20 = Clear: TextBox21 = Clear: TextBox22 = Clear
ListBox2.Clear
End Sub
Sub layzondertekst()
For Each layerObj In ThisDrawing.Layers
     mystr = Left(layerObj.Name, 5)
     mystr2 = Right(layerObj.Name, 1)
     
     If mystr = "groep" And mystr2 <> "h" Then
     splijt = Split(layerObj.Name, " ")
     splijt2 = Split(splijt(1), ".")
     If splijt2(0) = TextBox12 And splijt(0) = "groep" Then layerObj.Name = layerObj.Name & "h"
     End If 'mystr
Next 'layerobj
End Sub
Sub delwand()
ListBox1.Clear

Dim element As Object
For Each element In ThisDrawing.ModelSpace
      If element.ObjectName = "AcDbBlockReference" Then
      If element.Name = "groeptekstbloknew" Or element.Name = "GROEPTEKSTBLOKNEW" Then
      Set symbool = element
        If symbool.HasAttributes Then
        attributen = symbool.GetAttributes
        For I = LBound(attributen) To UBound(attributen)
        Set attribuut = attributen(I)
        If attribuut.TagString = "HOHAFSTAND" Then
           If attribuut.textstring = "Wandverwarming" Then
           For j = LBound(attributen) To UBound(attributen)
           Set attribuut = attributen(j)
            If attribuut.TagString = "GROEPTEKST" Then ListBox1.AddItem (attribuut.textstring)
           Next j
        End If 'TEXTBOX 9
      End If 'if unitnummer
    Next I
End If
End If
End If
Next element

teller = ListBox1.ListCount
For I = 0 To teller - 1
   'Define the text object
    tstring = ListBox1.List(I)
    tstring2 = Split(tstring, (" "))
    nostring = Split(tstring2(1), ("."))
     
    If nostring(0) = TextBox12 Then
        tstring3 = "wand " & tstring2(1) & "h"
        For Each layerObj In ThisDrawing.Layers
             If layerObj.Name = tstring Then layerObj.Name = tstring3
        Next 'layerobj
    End If
  Next I

End Sub
Private Sub CmdReset_Click()
Call RESET 'alle waardes op nul zetten
End Sub
Sub RESET()
cmdTelrollen.Enabled = False
ComboBox1.Clear: ComboBox2.Clear: ComboBox4.Clear
CheckBox1.Value = False: CheckBox2.Value = False
CheckBox6.Value = False: CheckBox7.Value = False
TextBox1 = Clear: TextBox2 = Clear: TextBox3 = Clear: TextBox4 = Clear
TextBox5 = Clear: TextBox6 = Clear: TextBox7 = Clear: TextBox15 = Clear: TextBox16 = Clear
TextBox14 = Clear: TextBox25 = Clear: TextBox26 = Clear
TextBox1 = "0": TextBox2 = "0": TextBox3 = "0": TextBox4 = "0"
TextBox5 = "0": TextBox6 = "0": TextBox7 = "0": TextBox15 = "0": TextBox16 = "0": TextBox11 = "0"
TextBox25 = "0": TextBox26 = "0": TextBox28 = "0"
TextBox15 = "0": TextBox16 = "0": TextBox17 = "0": TextBox9 = Clear
TextBox10 = Clear: TextBox18 = Clear: TextBox19 = Clear: TextBox20 = Clear: TextBox21 = Clear: TextBox13.Visible = False
TextBox9.Locked = False: OptionButton1.Value = True: TextBox22 = Clear
TextBox9.SetFocus
OptionButton5.Value = False
ToggleButton1.Value = False
TextBox1.Visible = True
TextBox2.Visible = True: TextBox3.Visible = True: TextBox4.Visible = True
TextBox5.Visible = True: TextBox6.Visible = True: TextBox7.Visible = True
TextBox15.Visible = True: TextBox16.Visible = True
Label1.Visible = True: Label2.Visible = True: Label3.Visible = True: Label4.Visible = True
Label5.Visible = True: Label6.Visible = True: Label7.Visible = True
Label27.Visible = True: Label28.Visible = True
Label1.Caption = "250 meter"
CmdBloklogo.Enabled = False 'knop plaatsen bloklogo
ComboBox4.Visible = False: Label26.Visible = False
ListBox1.Clear: ListBox2.Clear
Label30.Caption = "0"
'TextBox17.Enabled = False
frmGroeptekst.OptionButton7.Value = False
frmGroeptekst.OptionButton8.Value = False
CheckBox3.Value = False
TextBox27.Value = 0
CommandButton6.top = 256
Call Combolijst2
Call combolijst1
CommandButton7.Enabled = False
End Sub
Private Sub OptionButton1_Click()
'wth-zd
TextBox1.Visible = True: TextBox2.Visible = True: TextBox3.Visible = True:
TextBox4.Visible = True: TextBox5.Visible = True: TextBox6.Visible = True:
TextBox7.Visible = True: TextBox15.Visible = True: TextBox16.Visible = True:
Label1.Caption = "250 meter": Label2.Caption = "165 meter":
Label3.Caption = "125 meter": Label4.Caption = "105 meter": Label5.Caption = "90 meter"
Label6.Caption = "75 meter": Label7.Caption = "63 meter": Label27.Caption = "40 meter": Label27.Visible = True
Label28.Caption = "50 meter"
ComboBox4.Clear
ComboBox4.Visible = False: Label26.Visible = False
CmdBloklogo.top = 72
CommandButton6.top = 256
TextBox11.top = 198
Label22.top = 198
CheckBox8.Visible = False
Frame3.Height = 103
End Sub
Private Sub OptionButton9_Click()
'wth16*2,7
'TextBox1.Visible = False: TextBox2.Visible = False: TextBox3.Visible = False:
'Label1.Caption = "105 meter": Label2.Caption = "90 meter"
'Label3.Caption = "75 meter": Label4.Caption = "63 meter"
'Label5.Caption = Clear: Label27.Caption = Clear
'Label6.Caption = Clear: Label7.Caption = Clear: Label28.Caption = Clear
'TextBox4.Visible = True
'TextBox5.Visible = False: TextBox6.Visible = False:
'TextBox7.Visible = False: TextBox15.Visible = False: TextBox16.Visible = False
TextBox1.Visible = False: TextBox2.Visible = False: TextBox3.Visible = False:
TextBox4.Visible = True: TextBox5.Visible = True: TextBox6.Visible = True:
TextBox7.Visible = True: TextBox15.Visible = False: TextBox16.Visible = False:
Label1.Caption = "": Label2.Caption = ""
Label3.Caption = "": Label4.Caption = "105 meter": Label5.Caption = "90 meter"
Label6.Caption = "75 meter": Label7.Caption = "63 meter":  Label27.Caption = ""
Label28.Caption = ""
ComboBox4.Clear
ComboBox4.Visible = False: Label26.Visible = False
CmdBloklogo.top = 72
CommandButton6.top = 256
TextBox11.top = 198
Label22.top = 198
CheckBox8.Visible = False
Frame3.Height = 103
End Sub
Private Sub OptionButton2_Click()
'wth-pe-rt
TextBox1.Visible = True: TextBox2.Visible = True: TextBox3.Visible = True
TextBox4.Visible = False: TextBox5.Visible = False: TextBox6.Visible = False:
TextBox7.Visible = False: TextBox15.Visible = False: TextBox16.Visible = False:
Label4.Caption = Clear: Label5.Caption = Clear: Label27.Caption = Clear: Label27.Visible = False
Label6.Caption = Clear: Label7.Caption = Clear: Label28.Caption = Clear
Label1.Caption = "120 meter": Label2.Caption = "90 meter": Label3.Caption = "60 meter"
ComboBox4.Clear
ComboBox4.Visible = True: Label26.Visible = True
CmdBloklogo.top = 95
CommandButton6.top = 280
Frame3.Height = 127
TextBox11.top = 180
Label22.top = 180
CheckBox8.Visible = True
Call combolijst4
'Call leidingtype
End Sub
Private Sub OptionButton6_Click()
'wth-aluflex
If OptionButton6 = True Then
CheckBox2 = True
Else
CheckBox2 = False
End If
TextBox1.Visible = True: TextBox2.Visible = True: TextBox3.Visible = True
TextBox4.Visible = False: TextBox5.Visible = False: TextBox6.Visible = False:
TextBox7.Visible = False: TextBox15.Visible = False: TextBox16.Visible = False:
Label4.Caption = Clear: Label5.Caption = Clear: Label27.Caption = Clear: Label28.Caption = Clear
Label6.Caption = Clear: Label7.Caption = Clear: Label1.Caption = "200 meter"
Label2.Caption = "100 meter": Label3.Caption = "50 meter"
ComboBox4.Clear
ComboBox4.Visible = True: Label26.Visible = True
CmdBloklogo.top = 95
CommandButton6.top = 280
Frame3.Height = 127
TextBox11.top = 198
Label22.top = 198
CheckBox8.Visible = False
Call combolijst4
'Call leidingtype
End Sub
Private Sub TextBox9_DblClick(ByVal Cancel As MSForms.ReturnBoolean)
TextBox9 = ""
End Sub
Private Sub TextBox10_DblClick(ByVal Cancel As MSForms.ReturnBoolean)
TextBox10 = ""
End Sub
Private Sub TextBox1_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox1_DblClick(ByVal Cancel As MSForms.ReturnBoolean)
TextBox1 = ""
End Sub
Private Sub TextBox2_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox2_DblClick(ByVal Cancel As MSForms.ReturnBoolean)
TextBox2 = ""
End Sub
Private Sub TextBox3_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox3_DblClick(ByVal Cancel As MSForms.ReturnBoolean)
TextBox3 = ""
End Sub
Private Sub TextBox4_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox4_DblClick(ByVal Cancel As MSForms.ReturnBoolean)
TextBox4 = ""
End Sub
Private Sub TextBox5_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox5_DblClick(ByVal Cancel As MSForms.ReturnBoolean)
TextBox5 = ""
End Sub
Private Sub TextBox6_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox6_DblClick(ByVal Cancel As MSForms.ReturnBoolean)
TextBox6 = ""
End Sub
Private Sub TextBox7_Change()
TextBox11 = (Val(TextBox1)) + (Val(TextBox2)) + (Val(TextBox3)) + (Val(TextBox4)) + (Val(TextBox5)) + _
(Val(TextBox6)) + (Val(TextBox7))
End Sub
Private Sub TextBox7_DblClick(ByVal Cancel As MSForms.ReturnBoolean)
TextBox7 = ""
End Sub
Private Sub TextBox15_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox15_DblClick(ByVal Cancel As MSForms.ReturnBoolean)
TextBox15 = ""
End Sub
Private Sub TextBox16_Change()
TextBox11 = (Val(TextBox1)) + (Val(TextBox2)) + (Val(TextBox3)) + (Val(TextBox4)) + (Val(TextBox5)) + _
(Val(TextBox6)) + (Val(TextBox7)) + (Val(TextBox15)) + (Val(TextBox16))
End Sub
Private Sub TextBox16_DblClick(ByVal Cancel As MSForms.ReturnBoolean)
TextBox16 = ""
End Sub
Private Sub TextBox17_DblClick(ByVal Cancel As MSForms.ReturnBoolean)
TextBox17 = ""
End Sub
Private Sub TextBox17_Change()
On Error Resume Next
Dim b As Double
b = TextBox17.Text
  If Err Then
   TextBox17 = Clear
   TextBox17 = 0
   Exit Sub
  End If



If Label30.Caption = "0" Then Label30 = TextBox11
If TextBox17 = "0" Or TextBox17 = "" Then TextBox11 = Label30.Caption
TextBox11 = (Val(TextBox11)) + (Val(TextBox17))
End Sub
Private Sub TextBox9_Change()
Dim b As Double
On Error Resume Next
TextBox9.SetFocus
b = TextBox9.Text
If Err Then
   TextBox9 = Clear
   Cmdmeten.Enabled = False
   cmdTelrollen.Enabled = False
   Exit Sub
  End If
If TextBox9.Text <> "" And TextBox10.Text <> "" Then Cmdmeten.Enabled = True
If TextBox9.Text <> "" Then cmdTelrollen.Enabled = True
If TextBox9.Text <> "" Then CommandButton7.Enabled = True
Label33 = 0

TextBox1.Text = "0"
TextBox2.Text = "0"
TextBox3.Text = "0"
TextBox4.Text = "0"
TextBox5.Text = "0"
TextBox6.Text = "0"
TextBox7.Text = "0"
TextBox15.Text = "0"
TextBox16.Text = "0"
TextBox11.Text = "0"
'TextBox27 = Clear  ': TextBox27.Visible = False

End Sub
Private Sub TextBox10_Change()
Dim C As Double
On Error Resume Next
TextBox10.SetFocus
C = TextBox10.Text
If Err Then
   TextBox10 = Clear
   Cmdmeten.Enabled = False
   Exit Sub
  End If
If TextBox9.Text <> "" And TextBox10.Text <> "" Then Cmdmeten.Enabled = True
End Sub
Private Sub TextBox11_Change()
On Error Resume Next
Dim TA As Double
TA = TextBox11

'----30-6-2004-aangepast omdat ie de rollen niet goed optelde in sommige gevallen
TextBox11 = (Val(TextBox1)) + (Val(TextBox2)) + (Val(TextBox3)) + (Val(TextBox4)) + (Val(TextBox5)) + (Val(TextBox6)) + (Val(TextBox7)) + (Val(TextBox15)) + (Val(TextBox16)) + (Val(TextBox17))
'----30-6-2004-aangepast omdat ie de rollen niet goed optelde in sommige gevallen
Update
If Err Then
   TextBox11 = "0"
  Exit Sub
  End If

If TA > 20 And (frmGroeptekst.OptionButton7 = False And frmGroeptekst.OptionButton8 = False) Then
   'TextBox11.BackColor = &HFFFF&
   MsgBox "PAS OP!!, MEER DAN 20 groepen....!!!!", vbCritical
   TextBox1 = "0": TextBox2 = "0": TextBox3 = "0": TextBox4 = "0"
   TextBox5 = "0": TextBox6 = "0": TextBox7 = "0": TextBox15 = "0": TextBox16 = "0": TextBox11 = "0"
   Call RESET
   'TextBox11.BackColor = &HFFFFFF
   Exit Sub
End If

If Label33 = 0 Then
  If TextBox11 > 15 And ComboBox2 = "KMV" And (frmGroeptekst.OptionButton7 = False And frmGroeptekst.OptionButton8 = False) Then
   MsgBox "PAS OP!!, KMV-verdeler gaat maar tot 15 groepen....!!!!", vbCritical
   Label33 = 1
  End If
End If

If Label33 = 0 Then
  If TextBox11 > 16 And ComboBox2 = "HERZ" And (frmGroeptekst.OptionButton7 = False And frmGroeptekst.OptionButton8 = False) Then
   MsgBox "PAS OP!!, HERZ-verdeler gaat maar tot 16 groepen....!!!!", vbCritical
   Label33 = 1
  End If
End If

If TextBox11 <> "0" Then TextBox17.Enabled = True


End Sub
Private Sub TextBox12_Change()
Dim C As Double
On Error Resume Next

C = TextBox12.Text

If Err Then
   TextBox12 = Clear
   Exit Sub
  End If
End Sub
Private Sub TextBox18_Change()

Dim D As Double
On Error Resume Next

D = TextBox18.Text

If Err Then
   TextBox18 = Clear
    CommandButton5.Enabled = False
   Exit Sub
  End If
  If TextBox18.Text <> "" And TextBox19.Text <> "" And TextBox20.Text <> "" Then CommandButton5.Enabled = True
End Sub
Private Sub TextBox19_Change()
Dim e As Double
On Error Resume Next

e = TextBox19.Text

If Err Then
   TextBox19 = Clear
    CommandButton5.Enabled = False
   Exit Sub
  End If
  If TextBox18.Text <> "" And TextBox19.Text <> "" And TextBox20.Text <> "" Then CommandButton5.Enabled = True
End Sub
Private Sub TextBox20_Change()
Dim f As Double
On Error Resume Next

f = TextBox20.Text

If Err Then
   TextBox20 = Clear
   CommandButton5.Enabled = False
   Exit Sub
  End If
If TextBox18.Text <> "" And TextBox19.Text <> "" And TextBox20.Text <> "" Then CommandButton5.Enabled = True
End Sub
Private Sub Cmdmeten_Click()
ThisDrawing.SendCommand "ucs" & vbCr & "world" & vbCr
ThisDrawing.SendCommand "-layer" & vbCr & "U" & vbCr & "gt" & vbCr & vbCr
SendKeys "{capslock}"

On Error Resume Next
   Call Checktekst.Checktekst(a) 'kijken of de groeptekst al gebruikt is.
       If a = 1 Then
    Exit Sub
    End If
   
    'als groepslayer leeg is dan verwijderen i.v.m. dubbele
    'layernamen 1.01 en 1.01h bijvoorbeeld
        If TextBox23 = 1 Then
           Call Checklayer4.Checklayer4
           ThisDrawing.SetVariable "userr4", 0
        End If
    
    Dim RetObj As AcadObject
    Dim Pbase As Variant
    Dim mystr As String
    Dim mystr1 As String
    Dim zz As String
    On Error Resume Next
    eg = 0 'eerste groep
    cmdTelrollen.Enabled = True
        
    frmGroeptekst.Hide
    ThisDrawing.SendCommand "undo" & vbCr & "BE" & vbCr 'markeringspunt tussen elke unit
    ThisDrawing.SendCommand "-layer" & vbCr & "U" & vbCr & "*" & vbCr & vbCr
  
  
  
Opnieuw1:
    Lengte = 0  'lengte groep op nul zetten
    zlengte = 0
    Err.Clear
    

        
    ThisDrawing.Utility.GetEntity RetObj, Pbase, "Selecteer een lijn."
    
    
    If Err = 0 Then
    a = RetObj.startPoint
    b = a(2)
       If b <> 0 Then
            MsgBox "De Z-waarde's staan niet op nul.!!!!" & (Chr(13) & Chr(10)) & (Chr(13) & Chr(10)) & _
             "Ik zal nu proberen om de" & (Chr(13) & Chr(10)) & _
            "Z-waarde's voor je op nul te zetten.", vbExclamation
             ThisDrawing.SendCommand "Flatten" & vbCr
       End If
    End If
     
    
    If Err <> 0 Then
        Err.Clear
        TextBox10 = (Val(TextBox10)) + 1
        frmGroeptekst.Show
        Exit Sub
        'End
    End If
    
    
       
     
    mystr = Left(RetObj.Layer, 4)
    mystr1 = LCase(mystr)
    If mystr1 <> "groe" And mystr <> "wand" Then
        MsgBox " Let op, dit is geen vloer of wandgroep!!!!!", vbExclamation, "Let op"
        GoTo Opnieuw1
    End If
   
   If CheckBox2 = False And CheckBox6 = False Then Call M_Meten.Meten(RetObj, Pbase, eg)
   If CheckBox2 = True Then Call M_Meten_Werkelijk.Meten_Werkelijk(RetObj, Pbase, eg)
   If CheckBox6 = True Then Call M_Meten_Flexfix.Meten_Flexfix(RetObj, Pbase, eg)
   GoTo Opnieuw1
End Sub
Private Sub cmdTelrollen_Click()
check1 = 0
Call zoek_blok.zoek_blok
Call CHECKWERKLENG(check1)
'MsgBox check1

If frmGroeptekst.CheckBox2.Value = False Then Call nmeten 'standaard
If (frmGroeptekst.CheckBox2.Value = True And frmGroeptekst.CheckBox3.Value = False) And check1 = 0 Then Call nmetenw 'nieuwe tekeningen
'If (frmGroeptekst.CheckBox2.Value = True And frmGroeptekst.CheckBox3.Value = True) And check1 = 0 Then Call nmetenwoud 'oude tekeningen
check1 = 0
If frmGroeptekst.TextBox2 <> "0" And OptionButton1.Value = True Then Call waarschuwing.waarschuwing
End Sub
Sub CHECKWERKLENG(check1)
unittel = frmGroeptekst.TextBox9

If frmGroeptekst.CheckBox3.Value = False Then
   If unittel > 0 And unittel < 10 Then unitonder10 = "0" & frmGroeptekst.TextBox9
End If

If frmGroeptekst.CheckBox3.Value = False Then
   If unittel > 9 Then unitonder10 = frmGroeptekst.TextBox9
End If

If frmGroeptekst.CheckBox3.Value = True Then
   unitonder10 = frmGroeptekst.TextBox9
End If
'MsgBox unitonder10

Dim element As Object
For Each element In ThisDrawing.ModelSpace
      If element.ObjectName = "AcDbBlockReference" Then
      If element.Name = "groeptekstbloknew" Or element.Name = "GROEPTEKSTBLOKNEW" Then
      Set symbool = element
        If symbool.HasAttributes Then
        attributen = symbool.GetAttributes
        For I = LBound(attributen) To UBound(attributen)
        Set attribuut = attributen(I)
        If attribuut.TagString = "UNITNUMMER" Or attribuut.TagString = "unitnummer" Then
           If attribuut.textstring = unitonder10 Then
           
           For j = LBound(attributen) To UBound(attributen)
           Set attribuut = attributen(j)
            If attribuut.TagString = "WERKLENGTE" Then wklen = attribuut.textstring
            If wklen = "ja" Then
            check1 = 0
            Else
            check1 = 1
            End If
           Next j
        End If 'TEXTBOX 9
      End If 'if unitnummer
    Next I
End If
End If
End If
Next element
'MsgBox wklen

End Sub
Sub nmeten()

unittel = frmGroeptekst.TextBox9
'MsgBox "nmeten"
If frmGroeptekst.CheckBox3.Value = False Then
   If unittel > 0 And unittel < 10 Then unitonder10 = "0" & frmGroeptekst.TextBox9
End If
If frmGroeptekst.CheckBox3.Value = False Then
   If unittel > 9 Then unitonder10 = frmGroeptekst.TextBox9
End If
If frmGroeptekst.CheckBox3.Value = True Then
   unitonder10 = frmGroeptekst.TextBox9
End If

If CheckBox6.Value = True Then
    Dim element As Object
    For Each element In ThisDrawing.ModelSpace
          If element.ObjectName = "AcDbBlockReference" Then
          If element.Name = "groeptekstbloknew" Or element.Name = "GROEPTEKSTBLOKNEW" Then
          Set symbool = element
            If symbool.HasAttributes Then
            attributen = symbool.GetAttributes
            For I = LBound(attributen) To UBound(attributen)
            Set attribuut = attributen(I)
             If attribuut.TagString = "UNITNUMMER" Or attribuut.TagString = "unitnummer" Then
               If attribuut.textstring = unitonder10 Then
               For j = LBound(attributen) To UBound(attributen)
               Set attribuut = attributen(j)
                 If attribuut.TagString = "FLEXFIX" Then
                    ffch = attribuut.textstring
                    
                    For z = LBound(attributen) To UBound(attributen)
                    Set attribuut = attributen(z)
                       If attribuut.TagString = "TLVL" And ffch = "ja" Then
                       rolleesFF = attribuut.textstring
                         If rolleesFF <> " " Then
                          mystr = Split(rolleesFF, " ")
                          TextBox25 = (Val(TextBox25)) + mystr(0)
                          TextBox26 = (Val(TextBox26)) + 1
                          End If
                       'mystr = Left(ROLLEESFF, 3)
                       'MsgBox mystr(0)
                        End If 'rollengte
                        Next z
                 End If 'if not flexfix
    
              Next j
            End If 'TEXTBOX 9
          End If 'if unitnummer
    
        Next I
    End If
    End If
    End If
    Next element
End If 'checkbox6
            
Dim element200 As Object
    For Each element200 In ThisDrawing.ModelSpace
          If element200.ObjectName = "AcDbBlockReference" Then
          If element200.Name = "groeptekstbloknew" Or element200.Name = "GROEPTEKSTBLOKNEW" Then
          Set symbool = element200
            If symbool.HasAttributes Then
            attributen = symbool.GetAttributes
            For I = LBound(attributen) To UBound(attributen)
            Set attribuut = attributen(I)
             If attribuut.TagString = "UNITNUMMER" Or attribuut.TagString = "unitnummer" Then
               If attribuut.textstring = unitonder10 Then
               For j = LBound(attributen) To UBound(attributen)
               Set attribuut = attributen(j)
                 If attribuut.TagString = "FLEXFIX" Then
                    ffch = attribuut.textstring
                    
                    For z = LBound(attributen) To UBound(attributen)
                    Set attribuut = attributen(z)
                       If (attribuut.TagString = "ROLLENGTE" And attribuut.textstring <> "") And ffch <> "ja" Then
                            ROLLEES = attribuut.textstring
                            mystr = Left(ROLLEES, 3)
                            
                               For q = LBound(attributen) To UBound(attributen)
                                Set attribuut = attributen(q)
                                If attribuut.TagString = "TLVL" Then
                                   abc = attribuut.textstring
                                   If abc <> " " Then
                                   abcd = Split(abc, " ")
                                   frmGroeptekst.TextBox27 = Val(frmGroeptekst.TextBox27) + abcd(0)
                                   End If
                                 End If
                                Next q
                                
                            If frmGroeptekst.CheckBox1 = True Then
                              If mystr = TextBox14.Value Then TextBox1 = (Val(TextBox1)) + 1
                            End If
                            If mystr = 250 And OptionButton1.Value = True Then TextBox1 = (Val(TextBox1)) + 1
                            If mystr = 165 And OptionButton1.Value = True Then TextBox2 = (Val(TextBox2)) + 1
                            If mystr = 125 And OptionButton1.Value = True Then TextBox3 = (Val(TextBox3)) + 1
                            If mystr = 105 And OptionButton1.Value = True Then TextBox4 = (Val(TextBox4)) + 1
                            If mystr = 90 And OptionButton1.Value = True Then TextBox5 = (Val(TextBox5)) + 1
                            If mystr = 75 And OptionButton1.Value = True Then TextBox6 = (Val(TextBox6)) + 1
                            If mystr = 63 And OptionButton1.Value = True Then TextBox7 = (Val(TextBox7)) + 1
                            If mystr = 50 And OptionButton1.Value = True Then TextBox15 = (Val(TextBox15)) + 1
                            If mystr = 40 And OptionButton1.Value = True Then TextBox16 = (Val(TextBox16)) + 1
                            'wthzd 16*2,7
                            If mystr = 105 And OptionButton9.Value = True Then TextBox4 = (Val(TextBox4)) + 1
                            If mystr = 90 And OptionButton9.Value = True Then TextBox5 = (Val(TextBox5)) + 1
                            If mystr = 75 And OptionButton9.Value = True Then TextBox6 = (Val(TextBox6)) + 1
                            If mystr = 63 And OptionButton9.Value = True Then TextBox7 = (Val(TextBox7)) + 1
                            If OptionButton9.Value = True Then
                            TextBox1.Visible = False: TextBox2.Visible = False: TextBox3.Visible = False: TextBox15.Visible = False: TextBox16.Visible = False
                            Label1.Visible = False: Label2.Visible = False: Label3.Visible = False: Label27.Visible = False: Label28.Visible = False
                            End If
                            'PE-RT
                            If mystr = 120 And OptionButton2.Value = True Then TextBox1 = (Val(TextBox1)) + 1
                            If mystr = 90 And OptionButton2.Value = True Then TextBox2 = (Val(TextBox2)) + 1
                            If mystr = 60 And OptionButton2.Value = True Then TextBox3 = (Val(TextBox3)) + 1
                            'aluflex
                            If mystr = 200 And OptionButton6.Value = True Then TextBox1 = (Val(TextBox1)) + 1
                            If mystr = 100 And OptionButton6.Value = True Then TextBox2 = (Val(TextBox2)) + 1
                            If mystr = 50 And OptionButton6.Value = True Then TextBox3 = (Val(TextBox3)) + 1
                             
                        
                             
                             
                           
                        End If 'rollengte
                      Next z
                      
                      
                      
                 End If 'if not flexfix
    
              Next j
            End If 'TEXTBOX 9
          End If 'if unitnummer
    
        Next I
    End If
    End If
    End If
Next element200
 
TextBox11 = (Val(TextBox1)) + (Val(TextBox2)) + (Val(TextBox3)) + (Val(TextBox4)) + (Val(TextBox5)) + (Val(TextBox6)) + (Val(TextBox7)) + (Val(TextBox15)) + (Val(TextBox16)) + (Val(TextBox17))
CmdBloklogo.Enabled = True
cmdTelrollen.Enabled = False
TextBox1.Locked = False: TextBox2.Locked = False: TextBox3.Locked = False
TextBox4.Locked = False: TextBox5.Locked = False: TextBox6.Locked = False
TextBox7.Locked = False: TextBox15.Locked = False: TextBox16.Locked = False
TextBox9.Locked = False
TextBox9.SetFocus
Update
End Sub
Sub nmetenw()
'MsgBox "nmetenw"
unittel = frmGroeptekst.TextBox9

If frmGroeptekst.CheckBox3.Value = False Then
   If unittel > 0 And unittel < 10 Then unitonder10 = "0" & frmGroeptekst.TextBox9
End If
If frmGroeptekst.CheckBox3.Value = False Then
   If unittel > 9 Then unitonder10 = frmGroeptekst.TextBox9
End If
If frmGroeptekst.CheckBox3.Value = True Then
   unitonder10 = frmGroeptekst.TextBox9
End If

  Dim element As Object
  
    For Each element In ThisDrawing.ModelSpace
          If element.ObjectName = "AcDbBlockReference" Then
          If element.Name = "groeptekstbloknew" Or element.Name = "GROEPTEKSTBLOKNEW" Then
          Set symbool = element
            If symbool.HasAttributes Then
            attributen = symbool.GetAttributes
            For I = LBound(attributen) To UBound(attributen)
            Set attribuut = attributen(I)
             If attribuut.TagString = "UNITNUMMER" Or attribuut.TagString = "unitnummer" Then
               If attribuut.textstring = unitonder10 Then
               For j = LBound(attributen) To UBound(attributen)
               Set attribuut = attributen(j)
                 If attribuut.TagString = "FLEXFIX" Then
                    ffch = attribuut.textstring
                    
                    For z = LBound(attributen) To UBound(attributen)
                    Set attribuut = attributen(z)
                    
                       If (attribuut.TagString = "TLVL" And attribuut.textstring <> " ") And ffch = "ja" Then
                       'If attribuut.TagString = "ROLLENGTE" And ffch = "ja" Then
                       rolleesFF = attribuut.textstring
                         If rolleesFF <> " " Then
                          mystr = Split(rolleesFF, " ")
                          TextBox25 = (Val(TextBox25)) + mystr(0)
                          TextBox26 = (Val(TextBox26)) + 1
                          End If
                       'mystr = Left(ROLLEESFF, 3)
                       MsgBox mystr(0)
                        End If 'rollengte
                        Next z
                 End If 'if not flexfix
    
              Next j
            End If 'TEXTBOX 9
          End If 'if unitnummer
    
        Next I
    End If
    End If
    End If
    Next element

            
Dim element200 As Object

    For Each element200 In ThisDrawing.ModelSpace
          If element200.ObjectName = "AcDbBlockReference" Then
          If element200.Name = "groeptekstbloknew" Or element200.Name = "GROEPTEKSTBLOKNEW" Then
          Set symbool = element200
            If symbool.HasAttributes Then
            attributen = symbool.GetAttributes
            For I = LBound(attributen) To UBound(attributen)
            Set attribuut = attributen(I)
             If attribuut.TagString = "UNITNUMMER" Or attribuut.TagString = "unitnummer" Then
               If attribuut.textstring = unitonder10 Then
               For j = LBound(attributen) To UBound(attributen)
               Set attribuut = attributen(j)
                 If attribuut.TagString = "FLEXFIX" Then
                    ffch = attribuut.textstring
                    
                    For z = LBound(attributen) To UBound(attributen)
                    Set attribuut = attributen(z)
                       If (attribuut.TagString = "TLVL" And attribuut.textstring <> " ") And ffch <> "ja" Then
                       'MsgBox "ELEMENT200"
                      ROLLEES2 = Split(attribuut.textstring)
                     ' MsgBox attribuut.TextString
                 If ROLLEES2(0) <> "" Then
                     mystr2 = ROLLEES2(0)
                     Else
                     mystr2 = 0
                 End If
            'mystr2 = Left(ROLLEES2, 4)
            If OptionButton1.Value = True Then
            If frmGroeptekst.CheckBox1 = True Then
               If mystr2 = TextBox14.Value Then TextBox1 = (Val(TextBox1)) + 1
            End If
            If (mystr2 >= 162.5 And mystr2 < 247.5) And OptionButton1.Value = True Then TextBox1 = (Val(TextBox1)) + 1
            If (mystr2 >= 122.5 And mystr2 < 162.5) And OptionButton1.Value = True Then TextBox2 = (Val(TextBox2)) + 1
            If (mystr2 >= 102.5 And mystr2 < 122.5) And OptionButton1.Value = True Then TextBox3 = (Val(TextBox3)) + 1
            If (mystr2 >= 87.5 And mystr2 < 102.5) And OptionButton1.Value = True Then TextBox4 = (Val(TextBox4)) + 1
            If (mystr2 >= 72.5 And mystr2 < 87.5) And OptionButton1.Value = True Then TextBox5 = (Val(TextBox5)) + 1
            If (mystr2 >= 60.5 And mystr2 < 72.5) And OptionButton1.Value = True Then TextBox6 = (Val(TextBox6)) + 1
            If (mystr2 >= 47.5 And mystr2 < 60.5) And OptionButton1.Value = True Then TextBox7 = (Val(TextBox7)) + 1
            If (mystr2 >= 37.5 And mystr2 < 47.5) And OptionButton1.Value = True Then TextBox15 = (Val(TextBox15)) + 1
            If (mystr2 >= 10 And mystr2 < 37.5) And OptionButton1.Value = True Then TextBox16 = (Val(TextBox16)) + 1
            'frmGroeptekst.TextBox27.Visible = True
            totalrol = totalrol + Round(Val(mystr2), 1)
            frmGroeptekst.TextBox27 = Val(frmGroeptekst.TextBox27) + mystr2
            End If
            'PE-RT
            If OptionButton2.Value = True Then
            If (mystr2 >= 87.5 And mystr2 < 117.5) And OptionButton2.Value = True Then TextBox1 = (Val(TextBox1)) + 1
            If (mystr2 >= 57.5 And mystr2 < 87.5) And OptionButton2.Value = True Then TextBox2 = (Val(TextBox2)) + 1
            If (mystr2 >= 10 And mystr2 < 57.5) And OptionButton2.Value = True Then TextBox3 = (Val(TextBox3)) + 1
            If CheckBox8.Value = True And mystr2 >= 117.5 Then TextBox1 = (Val(TextBox1)) + 1
            'frmGroeptekst.TextBox27.Visible = True
            frmGroeptekst.TextBox27 = Val(frmGroeptekst.TextBox27) + mystr2
            totalrol = totalrol + Round(Val(mystr2), 1)
            End If
            'PE-RT 16 x 2,7
            If OptionButton9.Value = True And CheckBox2.Value = True Then
            If (mystr2 >= 87.5 And mystr2 < 125) Then TextBox4 = (Val(TextBox4)) + 1
            If (mystr2 >= 72.5 And mystr2 < 87.5) Then TextBox5 = (Val(TextBox5)) + 1
            If (mystr2 >= 60.5 And mystr2 < 72.5) Then TextBox6 = (Val(TextBox6)) + 1
            If (mystr2 >= 10 And mystr2 < 60.5) Then TextBox7 = (Val(TextBox7)) + 1
            TextBox1.Visible = False: TextBox2.Visible = False: TextBox3.Visible = False: TextBox15.Visible = False: TextBox16.Visible = False
            Label1.Visible = False: Label2.Visible = False: Label3.Visible = False: Label27.Visible = False: Label28.Visible = False
            'frmGroeptekst.TextBox27.Visible = True
            frmGroeptekst.TextBox27 = Val(frmGroeptekst.TextBox27) + mystr2
            totalrol = totalrol + Round(Val(mystr2), 1)
            End If
            'aluflex
            If OptionButton6.Value = True Then
            If (mystr2 >= 97.5 And mystr2 < 197.5) And OptionButton6.Value = True Then TextBox1 = (Val(TextBox1)) + 1
            If (mystr2 >= 47.5 And mystr2 < 97.5) And OptionButton6.Value = True Then TextBox2 = (Val(TextBox2)) + 1
            If (mystr2 >= 10 And mystr2 < 47.5) And OptionButton6.Value = True Then TextBox3 = (Val(TextBox3)) + 1
            'frmGroeptekst.TextBox27.Visible = True
            frmGroeptekst.TextBox27 = Val(frmGroeptekst.TextBox27) + mystr2
            totalrol = totalrol + Round(Val(mystr2), 1)
            End If
            End If 'ROLLENGTE
                        Next z
                 End If 'if not flexfix
    
              Next j
            End If 'TEXTBOX 9
          End If 'if unitnummer
    
        Next I
    End If
    End If
    End If
Next element200
 
frmGroeptekst.TextBox27 = totalrol
TextBox11 = (Val(TextBox1)) + (Val(TextBox2)) + (Val(TextBox3)) + (Val(TextBox4)) + (Val(TextBox5)) + (Val(TextBox6)) + (Val(TextBox7)) + (Val(TextBox15)) + (Val(TextBox16)) + (Val(TextBox17))
CmdBloklogo.Enabled = True
cmdTelrollen.Enabled = False
TextBox1.Locked = False: TextBox2.Locked = False: TextBox3.Locked = False
TextBox4.Locked = False: TextBox5.Locked = False: TextBox6.Locked = False
TextBox7.Locked = False: TextBox15.Locked = False: TextBox16.Locked = False
TextBox9.Locked = False
TextBox9.SetFocus
Update
End Sub
Sub combolijst1()
ComboBox1.Clear
ComboBox1.AddItem "Vlechtdraad"
ComboBox1.AddItem "Witmarmerbeugels"
ComboBox1.AddItem "Beugels/Nagels"
ComboBox1.AddItem "Eigen middelen"
ComboBox1.AddItem "IFD-Polystyreen"
ComboBox1.AddItem "Isoclips"
ComboBox1.AddItem "Keg"
ComboBox1.AddItem "Montagestrip"
ComboBox1.AddItem "Noppenplaat"
ComboBox1.AddItem "Schietbeugels"
ComboBox1.AddItem "Ty-raps"
ComboBox1.AddItem "Varisoclips"
ComboBox1.AddItem "Wedi Plaat"
'ComboBox1.listindex = 7
'ComboBox1.MatchEntry = fmMatchEntryFirstLetter
End Sub
Private Sub ComboBox2_Change()
'type unit
If ComboBox2.Value = "RUH-R" Or ComboBox2.Value = "RUH-RT" Then
  ComboBox3.Enabled = True
  Else
  ComboBox3.Enabled = False
 End If

If TextBox11 > 15 And ComboBox2 = "KMV" And (frmGroeptekst.OptionButton7.Value = False Or frmGroeptekst.OptionButton8.Value = False) Then
   MsgBox "PAS OP!!, KMV-verdeler gaat maar tot 15 groepen....!!!!", vbCritical
   End If
If TextBox11 > 12 And ComboBox2 = "VSKO" Then
   MsgBox "PAS OP!!, VSKO-verdeler gaat maar tot 12 groepen....!!!!", vbCritical
End If
If TextBox11 > 16 And ComboBox2 = "HERZ" And (frmGroeptekst.OptionButton7.Value = False Or frmGroeptekst.OptionButton8.Value = False) Then
   MsgBox "PAS OP!!, HERZ-verdeler gaat maar tot 16 groepen....!!!!", vbCritical
   End If
End Sub
Sub Combolijst2()
ComboBox2.AddItem "HERZ"
ComboBox2.AddItem "KMV"
ComboBox2.AddItem "LT"
ComboBox2.AddItem "LT-N"
ComboBox2.AddItem "LTS" 'aangepast
ComboBox2.AddItem "LTS-N" 'aangepast
ComboBox2.AddItem "LT-VK" 'aangepast
ComboBox2.AddItem "RINGLEIDING"
ComboBox2.AddItem "RUB-R"
ComboBox2.AddItem "RUB-RT"
ComboBox2.AddItem "RUBK-R"
ComboBox2.AddItem "RUBK-RT"
ComboBox2.AddItem "RUB-S"
ComboBox2.AddItem "RU-EE"
ComboBox2.AddItem "RUH-N"
ComboBox2.AddItem "RUH-R"
ComboBox2.AddItem "RUH-RT"
ComboBox2.AddItem "RUH-S"
ComboBox2.AddItem "RUV"
ComboBox2.AddItem "RU-WK"
ComboBox2.AddItem "RU-WKN" 'aangepast
ComboBox2.AddItem "RU-WKS" 'aangepast
ComboBox2.AddItem "RU-WW"
ComboBox2.AddItem "RU-WWN" 'aangepast
ComboBox2.AddItem "RU-WWS" 'aangepast
ComboBox2.AddItem "VSKO"
ComboBox2.ListIndex = 15
ComboBox2.MatchEntry = fmMatchEntryFirstLetter
End Sub
Sub Combolijst3()
ComboBox3.AddItem "KT220"
ComboBox3.AddItem "KT24"
ComboBox3.AddItem "TH7420"
ComboBox3.ListIndex = 2
ComboBox3.MatchEntry = fmMatchEntryFirstLetter
End Sub
Sub combolijst4()
 If OptionButton2.Value = True Then
 'ComboBox4.AddItem " "
 ComboBox4.AddItem "PE-RT 14*2 mm"
 ComboBox4.AddItem "PE-RT 16*2 mm"
 ComboBox4.AddItem "ALUFLEX 14*2 mm"
 ComboBox4.AddItem "ALUFLEX 16*2 mm"
 ComboBox4.AddItem "ALUFLEX 18*2 mm"
 ComboBox4.AddItem "ALUFLEX 20*2 mm"
 ComboBox4.AddItem "PE-RT 10*1,25 mm"
 'ComboBox4.AddItem "PE-RT 16*2,7 mm"
  ComboBox4.ListIndex = 1
 'ComboBox4.Text = ComboBox4.List(1)
 End If
 
 If OptionButton6.Value = True Then
 ComboBox4.AddItem "ALUFLEX 14*2 mm"
 ComboBox4.AddItem "ALUFLEX 16*2 mm"
 ComboBox4.AddItem "ALUFLEX 18*2 mm"
 ComboBox4.AddItem "ALUFLEX 20*2 mm"
 ComboBox4.ListIndex = 1
 'ComboBox4.Text = ComboBox4.List(1)
 End If
 
End Sub
Private Sub CmdBloklogo_Click()
On Error Resume Next
If ComboBox2 = "" Then
    MsgBox "Je bent 'Type unit' vergeten in te vullen..!!"
    ComboBox2.SetFocus
    Exit Sub
    End If
If ComboBox1 = "" Then
    MsgBox "Je bent 'Bevestigingsmateriaal' vergeten in te vullen..!!"
    ComboBox1.SetFocus
    Exit Sub
    End If
If ComboBox4 = "" And OptionButton6 = True Then
    MsgBox "Je bent 'Type buis' vergeten in te vullen..!!"
    ComboBox4.SetFocus
    Exit Sub
    End If
If ComboBox4 = "" And OptionButton2 = True Then
    MsgBox "Je bent 'Type buis' vergeten in te vullen..!!"
    ComboBox4.SetFocus
    Exit Sub
    End If
frmGroeptekst.Hide
TextBox9.Locked = False
    Set newLayer = ThisDrawing.Layers.Add("BLOKLOGO")
    ThisDrawing.ActiveLayer = newLayer
    Update
    ThisDrawing.SendCommand "-layer" & vbCr & "U" & vbCr & "*" & vbCr & vbCr
    Update
Call Schaal(scaal)
If (OptionButton1.Value = True Or OptionButton9.Value = True) And (TextBox11 = "0" And TextBox25 <> "0") Then
bestand = "c:\acad2002\dwg\Mat_spe_FLEX.dwg"
'MsgBox bestand
Else
 If OptionButton1.Value = True Then bestand = "c:\acad2002\dwg\Mat_spe_ZD.dwg"
 If OptionButton9.Value = True Then bestand = "c:\acad2002\dwg\Mat_spe_ZD_1627.dwg"
End If

If OptionButton2.Value = True Then bestand = "c:\acad2002\dwg\Mat_spe_PE.dwg"
If OptionButton6.Value = True Then bestand = "c:\acad2002\dwg\Mat_spe_ALU.dwg"
If OptionButton1.Value = True And (frmGroeptekst.OptionButton7 = True Or frmGroeptekst.OptionButton8 = True) Then bestand = "c:\acad2002\dwg\Mat_spe_ZDringleiding.dwg"
If OptionButton9.Value = True And (frmGroeptekst.OptionButton7 = True Or frmGroeptekst.OptionButton8 = True) Then bestand = "c:\acad2002\dwg\Mat_spe_ZDringleiding.dwg"
If OptionButton2.Value = True And (frmGroeptekst.OptionButton7 = True Or frmGroeptekst.OptionButton8 = True) Then bestand = "c:\acad2002\dwg\Mat_spe_PEringleiding.dwg"
If OptionButton6.Value = True And (frmGroeptekst.OptionButton7 = True Or frmGroeptekst.OptionButton8 = True) Then bestand = "c:\acad2002\dwg\Mat_spe_ALUringleiding.dwg"
If frmGroeptekst.CheckBox8.Value = True Then bestand = "c:\acad2002\dwg\Mat_spe_PE800.dwg"
If frmGroeptekst.CheckBox2.Value = True And OptionButton9.Value = True Then bestand = "c:\acad2002\dwg\Mat_spe_ZD_1627500.dwg"
bestand20 = "c:\acad2002\dwg\Mat_spe_FLEX_Aankoppel.dwg"

If frmGroeptekst.TextBox29 <> "" Then scaal = frmGroeptekst.TextBox29
Dim pb1 As Variant
pb1 = ThisDrawing.Utility.GetPoint(, "Plaats startpunt....")
Set blockRefObj = ThisDrawing.ModelSpace.InsertBlock(pb1, bestand, scaal, scaal, 1, 0)
If TextBox11 <> "0" And TextBox25 <> "0" Then Set blockRefObj = ThisDrawing.ModelSpace.InsertBlock(pb1, bestand20, scaal, scaal, 1, 0)
Update
    If Err Then
    frmGroeptekst.Show
    Exit Sub
    End If
    
Dim element2 As Object
If (OptionButton1.Value = True Or OptionButton9.Value = True) Then
aantal_groepen = (Val(TextBox1)) + (Val(TextBox2)) + (Val(TextBox3)) + (Val(TextBox4)) + (Val(TextBox5)) + _
(Val(TextBox6)) + (Val(TextBox7)) + (Val(TextBox15)) + (Val(TextBox16)) + (Val(TextBox17))
If (Val(TextBox1)) = 0 Then TextBox1 = "-"
If (Val(TextBox2)) = 0 Then TextBox2 = "-"
If (Val(TextBox3)) = 0 Then TextBox3 = "-"
If (Val(TextBox4)) = 0 Then TextBox4 = "-"
If (Val(TextBox5)) = 0 Then TextBox5 = "-"
If (Val(TextBox6)) = 0 Then TextBox6 = "-"
If (Val(TextBox7)) = 0 Then TextBox7 = "-"
If (Val(TextBox15)) = 0 Then TextBox15 = "-"
If (Val(TextBox16)) = 0 Then TextBox16 = "-"
aantal_groepen = aantal_groepen + (Val(TextBox26))

If ComboBox3.Enabled = False Then
REGELTYPE = ComboBox2 & " " & aantal_groepen 'ZONDER REGELING
Else
REGELTYPE = ComboBox2 & " " & aantal_groepen & "/" & ComboBox3 'met regeling
End If
If frmGroeptekst.OptionButton7 = True Or frmGroeptekst.OptionButton8 = True Then REGELTYPE = ComboBox2

If ComboBox2 = "RUW-Groot" Or ComboBox2 = "RUW-Klein" Then
REGELTYPE = "RUW" & " " & aantal_groepen
End If
'bloklogo invullen WTH-ZD

unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element2 In ThisDrawing.ModelSpace
      If element2.ObjectName = "AcDbBlockReference" Then
      If UCase(element2.Name) = "MAT_SPE_ZD" Or element2.Name = "Mat_spe_ZDringleiding" _
      Or element2.Name = "Mat_spe_ZD_1627" Then
      Set symbool = element2
        If symbool.HasAttributes Then
        attributen = symbool.GetAttributes
        For I = LBound(attributen) To UBound(attributen)
        Set attribuut = attributen(I)
        If attribuut.TagString = "RNU" And attribuut.textstring = "" Then attribuut.textstring = unitonder10 'REGELUNITNUMMER
        If attribuut.TagString = "WTHZD" And OptionButton1.Value = True And attribuut.textstring = "" Then attribuut.textstring = "WTH-ZD 20*3,4 mm" 'TYPE BUIS
        If attribuut.TagString = "WTHZD" And OptionButton9.Value = True And attribuut.textstring = "" Then attribuut.textstring = "WTH-ZD 16*2,7 mm" 'TYPE BUIS
        If attribuut.TagString = "WTH250" And attribuut.textstring = "" Then attribuut.textstring = TextBox1  '250 METER
        If attribuut.TagString = "WTH165" And attribuut.textstring = "" Then attribuut.textstring = TextBox2  '165 METER
        If attribuut.TagString = "WTH125" And attribuut.textstring = "" Then attribuut.textstring = TextBox3  '125 METER
        If attribuut.TagString = "WTH105" And attribuut.textstring = "" Then attribuut.textstring = TextBox4  '105 METER
        If attribuut.TagString = "WTH90" And attribuut.textstring = "" Then attribuut.textstring = TextBox5  '90 METER
        If attribuut.TagString = "WTH75" And attribuut.textstring = "" Then attribuut.textstring = TextBox6  '75 METER
        If attribuut.TagString = "WTH63" And attribuut.textstring = "" Then attribuut.textstring = TextBox7  '63 METER
        If attribuut.TagString = "WTH50" And attribuut.textstring = "" Then attribuut.textstring = TextBox15  '40 METER
        If attribuut.TagString = "WTH40" And attribuut.textstring = "" Then attribuut.textstring = TextBox16  '50 METER
        If attribuut.TagString = "REGELUNITTYPE" And attribuut.textstring = "" Then attribuut.textstring = REGELTYPE  'TYPE REGELUNIT
        If attribuut.TagString = "BEVESTIGINGSTYPE" And attribuut.textstring = "" Then attribuut.textstring = ComboBox1  'BEVESTIGING
        If attribuut.TagString = "ROLGROTER250" And CheckBox1.Value = True Then attribuut.textstring = TextBox14 & " meter :" 'ROL GROTER DAN 250 METER
       Next I
       
      End If
      End If
      End If
  Next element2
 End If
 Update
 
 
 For Each element13 In ThisDrawing.ModelSpace
      If element13.ObjectName = "AcDbBlockReference" Then
      If UCase(element13.Name) = "MAT_SPE_ZD_1627500" Then
      Set symbool = element13
        If symbool.HasAttributes Then
        attributen = symbool.GetAttributes
         For w = LBound(attributen) To UBound(attributen)
         Set attribuut = attributen(w)
         If attribuut.TagString = "RNU" And attribuut.textstring = "" Then attribuut.textstring = unitonder10 'REGELUNITNUMMER
         If attribuut.TagString = "PE" And attribuut.textstring = "" Then attribuut.textstring = "WTH-ZD 16*2,7 mm"
         If attribuut.TagString = "REGELUNITTYPE" And attribuut.textstring = "" Then attribuut.textstring = REGELTYPE  'TYPE REGELUNIT
         If attribuut.TagString = "BEVESTIGINGSTYPE" And attribuut.textstring = "" Then attribuut.textstring = ComboBox1  'BEVESTIGING
         If attribuut.TagString = "LMETER" And attribuut.textstring = "" Then attribuut.textstring = Round(Val(TextBox27), 1)
         Next w
        
        End If
      End If
      End If
  Next element13
 
 
 For Each element6 In ThisDrawing.ModelSpace
      If element6.ObjectName = "AcDbBlockReference" Then
      If UCase(element6.Name) = "MAT_SPE_FLEX" Or element6.Name = "Mat_spe_FLEX_Aankoppel" Then
      Set symbool = element6
        If symbool.HasAttributes Then
        attributen = symbool.GetAttributes
        For I = LBound(attributen) To UBound(attributen)
        Set attribuut = attributen(I)
        If attribuut.TagString = "RNU" And attribuut.textstring = "" Then attribuut.textstring = unitonder10 'REGELUNITNUMMER
        If attribuut.TagString = "FLEX_BUIS" And attribuut.textstring = "" Then attribuut.textstring = "WTH-ZD 16*2,7 mm" 'REGELUNITNUMMER
        If attribuut.TagString = "FLEX_METERS" And attribuut.textstring = "" Then attribuut.textstring = TextBox25  'AANTAL METER
        If attribuut.TagString = "FLEX_MATTEN" And attribuut.textstring = "" Then attribuut.textstring = TextBox26  'AANTAL METER
        If attribuut.TagString = "REGELUNITTYPE" And attribuut.textstring = "" Then attribuut.textstring = REGELTYPE  'TYPE REGELUNIT
        If attribuut.TagString = "BEVESTIGINGSTYPE" And attribuut.textstring = "" Then attribuut.textstring = ComboBox1  'BEVESTIGING
       Next I
       
      End If
      End If
      End If
  Next element6

 Update
 
 Dim element3 As Object
If OptionButton2.Value = True Then
aantal_groepen = (Val(TextBox1)) + (Val(TextBox2)) + (Val(TextBox3)) + (Val(TextBox17))
If (Val(TextBox1)) = 0 Then TextBox1 = "-"
If (Val(TextBox2)) = 0 Then TextBox2 = "-"
If (Val(TextBox3)) = 0 Then TextBox3 = "-"
If ComboBox3.Enabled = False Then
REGELTYPE = ComboBox2 & " " & aantal_groepen
Else
REGELTYPE = ComboBox2 & " " & aantal_groepen & "/" & ComboBox3
End If
If frmGroeptekst.OptionButton7 = True Or frmGroeptekst.OptionButton8 = True Then REGELTYPE = ComboBox2

'PE-RT
unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element3 In ThisDrawing.ModelSpace
      If element3.ObjectName = "AcDbBlockReference" Then
      If UCase(element3.Name) = "MAT_SPE_PE" Or element3.Name = "Mat_spe_PEringleiding" Or element3.Name = "Mat_spe_PE800" Then
      Set symbool = element3
        If symbool.HasAttributes Then
        attributen = symbool.GetAttributes
        For j = LBound(attributen) To UBound(attributen)
        Set attribuut = attributen(j)
        If attribuut.TagString = "RNU" And attribuut.textstring = "" Then attribuut.textstring = unitonder10 'REGELUNITNUMMER
        If attribuut.TagString = "PE" And attribuut.textstring = "" Then attribuut.textstring = ComboBox4 'TYPE BUIS
        If CheckBox8.Value = False Then If attribuut.TagString = "PE120" And attribuut.textstring = "" Then attribuut.textstring = TextBox1  '120 METER
        If CheckBox8.Value = False Then If attribuut.TagString = "PE90" And attribuut.textstring = "" Then attribuut.textstring = TextBox2  '90 METER
        If CheckBox8.Value = False Then If attribuut.TagString = "PE60" And attribuut.textstring = "" Then attribuut.textstring = TextBox3  '60 METER
        If attribuut.TagString = "REGELUNITTYPE" And attribuut.textstring = "" Then attribuut.textstring = REGELTYPE  'TYPE REGELUNIT
        If attribuut.TagString = "BEVESTIGINGSTYPE" And attribuut.textstring = "" Then attribuut.textstring = ComboBox1  'BEVESTIGING
        If attribuut.TagString = "LMETER" And attribuut.textstring = "" Then attribuut.textstring = Round(Val(TextBox27), 1)
    Next j
       
        End If
      End If
      End If
  Next element3
  
 End If
  Update
 

  
  

  
   Dim element4 As Object
If OptionButton6.Value Then
aantal_groepen = (Val(TextBox1)) + (Val(TextBox2)) + (Val(TextBox3)) + (Val(TextBox17))
If (Val(TextBox1)) = 0 Then TextBox1 = "-"
If (Val(TextBox2)) = 0 Then TextBox2 = "-"
If (Val(TextBox3)) = 0 Then TextBox3 = "-"
If ComboBox3.Enabled = False Then
REGELTYPE = ComboBox2 & " " & aantal_groepen
Else
REGELTYPE = ComboBox2 & " " & aantal_groepen & "/" & ComboBox3
End If
If frmGroeptekst.OptionButton7 = True Or frmGroeptekst.OptionButton8 = True Then REGELTYPE = ComboBox2

'ALUFLEX
unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element4 In ThisDrawing.ModelSpace
      If element4.ObjectName = "AcDbBlockReference" Then
      If UCase(element4.Name) = "MAT_SPE_ALU" Or element4.Name = "Mat_spe_ALUringleiding" Then
      Set symbool = element4
        If symbool.HasAttributes Then
        attributen = symbool.GetAttributes
        For j = LBound(attributen) To UBound(attributen)
        Set attribuut = attributen(j)
        If attribuut.TagString = "RNU" And attribuut.textstring = "" Then attribuut.textstring = unitonder10 'REGELUNITNUMMER
        If attribuut.TagString = "ALU" And attribuut.textstring = "" Then attribuut.textstring = ComboBox4 'TYPE BUIS
        If attribuut.TagString = "ALU200" And attribuut.textstring = "" Then attribuut.textstring = TextBox1  '120 METER
        If attribuut.TagString = "ALU100" And attribuut.textstring = "" Then attribuut.textstring = TextBox2  '90 METER
        If attribuut.TagString = "ALU50" And attribuut.textstring = "" Then attribuut.textstring = TextBox3  '60 METER
        If attribuut.TagString = "REGELUNITTYPE" And attribuut.textstring = "" Then attribuut.textstring = REGELTYPE  'TYPE REGELUNIT
        If attribuut.TagString = "BEVESTIGINGSTYPE" And attribuut.textstring = "" Then attribuut.textstring = ComboBox1  'BEVESTIGING
        If attribuut.TagString = "PEALU200" And OptionButton6 = True Then attribuut.textstring = "200 meter :" 'Aluflex 200 METER
        If attribuut.TagString = "PEALU100" And OptionButton6 = True Then attribuut.textstring = "100 meter :" 'Aluflex 100 METER
        If attribuut.TagString = "PEALU50" And OptionButton6 = True Then attribuut.textstring = " 50 meter :" 'Aluflex 100 METER
       Next j
       
        End If
      End If
      End If
  Next element4
 End If
  Update
  
  
  
  Dim pb2(0 To 2) As Double
  If OptionButton1.Value = True Or OptionButton9.Value = True Then zakken = 210
  If OptionButton2.Value = True Or OptionButton6.Value = True Then zakken = 179
  If OptionButton9.Value = True And CheckBox2.Value = True Then zakken = 177
  If TextBox11 = "0" And TextBox25 <> "0" Then zakken = 179
  
  pb2(0) = pb1(0) - (scaal * 460)
  pb2(1) = pb1(1) + (scaal * zakken) '179) '177'210)
  pb2(2) = pb1(2)
  
  'juiste regelunitblokje.dwg inserten in de tekening
  bestand2 = ComboBox2 & ".dwg"
  If ComboBox2 = "RUW-Groot" Then bestand2 = "RUW" & ".dwg"
  If ComboBox2 = "RUW-Klein" Then bestand2 = "RUW" & ".dwg"
  If ComboBox2 = "RUB-R" And aantal_groepen > 4 Then bestand2 = "RUH-R" & ".dwg"
  If ComboBox2 = "RUB-RT" And aantal_groepen > 4 Then bestand2 = "RUH-RT" & ".dwg"
  If ComboBox2 = "RUB-S" And aantal_groepen > 0 Then bestand2 = "RUH-S" & ".dwg"
  If ComboBox2 = "VSKO" Then bestand2 = "VSKO-B" & ".dwg"
  bestand3 = "c:\acad2002\dwg\" & ComboBox2 & ".txt"  'tekstbestand met afmetingen
  If ComboBox2 = "VSKO" Then bestand3 = "c:\acad2002\dwg\" & ComboBox2 & "-B.txt"  'tekstbestand met afmetingen
  
  Update
  
  Call Unitblok.Unitblok(aantal_groepen, pb2, bestand2, bestand3, scaal)
  Call RESET
  Unload Me
  'frmGroeptekst.Show
  'Unload Me
End Sub

Sub Schaal(scaal)
frmGroeptekst.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
Update
End Sub
Private Sub CommandButton7_Click()
unittel = frmGroeptekst.TextBox9

If frmGroeptekst.CheckBox3.Value = False Then
   If unittel > 0 And unittel < 10 Then unitonder10 = "0" & frmGroeptekst.TextBox9
End If

If frmGroeptekst.CheckBox3.Value = False Then
   If unittel > 9 Then unitonder10 = frmGroeptekst.TextBox9
End If

If frmGroeptekst.CheckBox3.Value = True Then
   unitonder10 = frmGroeptekst.TextBox9
End If



 For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                         Set attribuut = attributen(I)
                         If attribuut.TagString = "UNITNUMMER" Or attribuut.TagString = "unitnummer" Then
                          If attribuut.textstring = unitonder10 Then
                             For n = LBound(attributen) To UBound(attributen)
                             Set attribuut = attributen(n)
                         
                             If attribuut.TagString = "TLVL" Then attribuut.textstring = " "
                             Next n
                         
                          End If
                        End If
       
                    Next I
                End If
            End If
        End If
    Next element
    Update
End Sub

Attribute VB_Name = "frmInregelstaat"
Attribute VB_Base = "0{21B414CE-BDC5-4AB8-B450-CB778C4C817C}{65C989D0-4F00-4E67-9CA2-7042A8745251}"
Attribute VB_GlobalNameSpace = False
Attribute VB_Creatable = False
Attribute VB_PredeclaredId = True
Attribute VB_Exposed = False
Attribute VB_TemplateDerived = False
Attribute VB_Customizable = False
'24-01-2007 Inregelstaat genereren
'G.C.Haak
#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
 
 On Error Resume Next
 Call kaderuit  'schaal kader uitlezen
 TextBox20 = ThisDrawing.GetVariable("dwgprefix")
 Call extreemtek
 
 'Kill ("c:\acad2002\Inregelstaat.txt")
 If TextBox14 > 30 Then Call importuserr2
 If TextBox14 < 31 Then TextBox13 = ThisDrawing.GetVariable("USERR2")
 
 ComboBox1.AddItem "2.5"
 ComboBox1.AddItem "2"
 ComboBox1.Text = ComboBox1.List(0)
Call wandvv
'Call Checklayer2.Checklayer2
End Sub
Private Sub wandvv()
    For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                         Set attribuut = attributen(I)
                         'If attribuut.TagString = "GROEPTEKST" Then GRP = attribuut.textstring
                         If attribuut.TagString = "HOHAFSTAND" Then WH = attribuut.textstring
                         
                    Next I
                End If
            End If
        End If
    Next element
    
   If WH = "Wandverwarming" Then
   
     MsgBox "Er is wandverwarming in de tekening aanwezig.!!!!" & (Chr(13) & Chr(10)) & (Chr(13) & Chr(10)) & _
            "Vul de hoogte van de wandverwarming in. (standaard staat ie op 2,5 meter)", vbExclamation ' & (Chr(13) & Chr(10)) & _
            '"Als je meerdere hoogte's heb vul dan de grootste waarde in, of een gemiddelde waarde.", vbExclamation
    frmInregelstaat.Height = 134
    frmInregelstaat.cmdLayers.top = 78
    frmInregelstaat.cmdAfsluiten.top = 78
    frmInregelstaat.Label39.Visible = True
    frmInregelstaat.ComboBox1.Visible = True
   End If
End Sub
Private Sub kaderuit()

Dim element As Object
For Each element In ThisDrawing.ModelSpace
      If element.ObjectName = "AcDbBlockReference" Then
      If UCase(element.Name) = "KADERLOGO" Or UCase(element.Name) = "LOGOTGH" Then
      Set symbool = element
        If symbool.HasAttributes Then
        attributen = symbool.GetAttributes
        For I = LBound(attributen) To UBound(attributen)
        Set attribuut = attributen(I)
        If attribuut.TagString = "OPDRACHTGEVER" Then ListBox4.AddItem ("OPDRACHTGEVER" & "#" & attribuut.textstring)
        If attribuut.TagString = "PLAATS" Then ListBox4.AddItem ("PLAATS" & "#" & attribuut.textstring)
        If attribuut.TagString = "PROJECTNAAM" Then ListBox4.AddItem ("PROJECTNAAM" & "#" & attribuut.textstring)
        If attribuut.TagString = "MONTAGEADRES" Then ListBox4.AddItem ("MONTAGEADRES" & "#" & attribuut.textstring)
        If attribuut.TagString = "MONTAGEPLAATS" Then ListBox4.AddItem ("MONTAGEPLAATS" & "#" & attribuut.textstring)
        If attribuut.TagString = "PROJECTNUMMER" Then ListBox4.AddItem ("PROJECTNUMMER" & "#" & attribuut.textstring)
        If attribuut.TagString = "BLAD" Then ListBox4.AddItem ("BLAD" & "#" & attribuut.textstring)
       
        Next I
       End If
     End If
   End If
  Next element
End Sub
Sub exportuserr2()
TT = ThisDrawing.GetVariable("USERR2")
Const ForReading = 1, ForWriting = 2, ForAppending = 8
Dim fg, fh
'Dim s1 As AcadSelectionSet
Set fg = CreateObject("Scripting.FileSystemObject")

Set fh = fg.OpenTextFile("c:\acad2002\userr2.txt", ForWriting, -2)
    fh.write TT
    fh.Close
End Sub
Sub importuserr2()
Const ForReading = 1, ForWriting = 2, ForAppending = 3
Const TristateUseDefault = -2, TristateTrue = -1, TristateFalse = 0
Dim fl, m, TS
Set fl = CreateObject("Scripting.FileSystemObject")
Set m = fl.OpenTextFile("c:\acad2002\userr2.txt", ForReading, False)
    TS = m.ReadLine
    TextBox13 = TS
m.Close 'sluiten van tekstbestand
End Sub
Private Sub TextBox1_Change()
If TextBox1 <> "" Then CommandButton1.Locked = False
End Sub
Private Sub cmdLayers_Click()

ListBox1.Clear
ListBox2.Clear
Update
On Error Resume Next
  
 Dim cirkel As Object
 Dim element As Object
 Dim Lengte As Double
 Dim laagobj As Object
 
 Dim minaantal As Integer
 Dim maxaantal As Integer
 Dim I As Integer
 I = 0
 minaantal = 0
 maxaantal = ThisDrawing.Layers.Count
 For Each laagobj In ThisDrawing.Layers
    I = I + 1
    ProgressBar1.Min = minaantal
    ProgressBar1.Max = maxaantal
    ProgressBar1.Value = I
 
      mystr = Left(laagobj.Name, 5)
      mystcontr = Len(laagobj.Name)
      
      If mystr = "GROEP" Then mystr = "groep"


      If mystr = "groep" And mystcontr = 11 Then

'''''7-2-2007
'''''      If Not mystr = "groep" Then
'''''      GoTo wand
'''''      Else
        
        
        For Each element In ThisDrawing.ModelSpace
          If element.Layer = laagobj.Name Then
                'BEREKENEN TOTALE LENGTE
                If element.EntityName = "AcDbLine" Then Lengte = Lengte + element.Length
                If element.EntityName = "AcDbArc" Then Lengte = Lengte + element.ArcLength
          End If 'elementlayer
            
        Next element
              
              
              For Each cirkel In ThisDrawing.ModelSpace
                If cirkel.Layer = laagobj.Name Then
                If cirkel.EntityName = "AcDbCircle" Then
                z = z + 1
                'wvaanwezig = " (WV)"
                
                zlengte = (z * (ComboBox1.Text * 100)) + 100    '
                End If
                End If
              Next cirkel
         
                
                
'''''7-2-2007
'''''wand:
'''''        If mystr = "WAND_" Then mystr = "wand_"
'''''        If mystr = "wand_" Then
'''''             For Each element In ThisDrawing.ModelSpace
'''''             If element.Layer = laagobj.Name Then
'''''                'BEREKENEN TOTALE LENGTE
'''''                If element.EntityName = "AcDbLine" Then Lengte = Lengte + element.Length
'''''                If element.EntityName = "AcDbArc" Then Lengte = Lengte + element.ArcLength
'''''
'''''             End If 'elementlayer
'''''             Next element
'''''
'''''                For Each cirkel In ThisDrawing.ModelSpace
'''''                If cirkel.Layer = laagobj.Name Then
'''''                If cirkel.EntityName = "AcDbCircle" Then
'''''                z = z + 1
'''''                wvaanwezig = " (WV)"
'''''                End If
'''''                End If
'''''                Next cirkel
'''''                zlengte = (z * (ComboBox1.Text * 100)) + 100
'''''                End If '2e mystr


                
    Lengte = (Lengte * TextBox19) + zlengte
    'Lengte = Lengte + zlengte
    Lengte = Lengte / 100
    Lengte = Fix(Lengte)
    Lengte = Lengte + 1
    Lengte = Round(Lengte, 1)
    
    'totalrollen = totalrollen + Lengte
  

  If mystr = "groep" Or mystr = "GROEP" Then
  t = Split(laagobj.Name, " ")
  
  
  D = t(1) & "#" & Lengte 'laagobj.Name
  'D = laagobj.Name & "#" & Lengte 'laagobj.Name
  ListBox1.AddItem (D)
  End If

    Lengte = 0 'Lengte leeggooien voordat de volgende groep wordt gemeten
    zlengte = 0
    z = 0
'''''    wvaanwezig = ""
'''''7-2-2007'''''End If  'end if  mystr

   End If 'mystr + mystrcontr
 Next laagobj
 ProgressBar1.Value = minaantal
 Update
 

 Cmdprint.Enabled = True

   'lijst rangschikken
  Dim Veld(0 To 500)
  Dim textstring2 As String
  
    For I = 0 To ListBox1.ListCount - 1
    textstring2 = ListBox1.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox1.Clear
 
  For x = 0 To UBound(Veld)
  If Veld(x) <> "" Then ListBox1.AddItem Veld(x)
  Next x
 
'''' ONDERSTAANDE REGELS LATEN STAAN
'''' Dim textstring3
'''' teller = ListBox1.ListCount
'''' For j = 0 To teller - 1
''''    textstring2 = ListBox1.List(j)
''''    textstring3 = Split(textstring2, ("#"))
''''    Dim a
''''    a = textstring3(0)
''''    Dim b
''''    b = textstring3(1)
''''    'MsgBox textstring3(0)
''''    ListBox2.AddItem (a)
''''    ListBox3.AddItem (b)
''''
'''' Next j

 Call Cmdprint_Click
End Sub
Private Sub Cmdprint_Click()
Const ForReading = 1, ForWriting = 2, ForAppending = 8
Dim fs, f
Dim s1 As AcadSelectionSet
Set fs = CreateObject("Scripting.FileSystemObject")
teknaam = ThisDrawing.GetVariable("dwgname")
pad = ThisDrawing.GetVariable("dwgprefix")
usernaam = ThisDrawing.GetVariable("loginname")
Dim MyDate
MyDate = DateValue(Date)    ' Return a date.


Dim xlsnaam
xlsnaam = TextBox20 & TextBox17 & ".xls"
Dim textstring
Dim textstring2

Set f = fs.OpenTextFile(xlsnaam, ForWriting, -2) ' "c:\acad2002\Inregelstaat.xls"
    teller3 = ListBox4.ListCount
    For k = 0 To teller3 - 1
       'Define the text object
        textstring5 = ListBox4.List(k)
        textstring6 = Split(textstring5, ("#"))
        f.write textstring6(0)
        f.write Chr(9)
        f.write textstring6(1)
        f.write Chr(13) + Chr(10)
     Next k
     f.write Chr(13) + Chr(10)
f.Close


    teller = ListBox1.ListCount
    For I = 0 To teller - 1
       'Define the text object
        textstring = ListBox1.List(I)
        textstring2 = Split(textstring, ("#"))
        Set f = fs.OpenTextFile(xlsnaam, ForAppending, -2)
        f.write textstring2(0)
        f.write Chr(9)
        f.write textstring2(1)
        f.write Chr(13) + Chr(10)
        f.Close
    Next I

    If TextBox14 > 30 Then ThisDrawing.Close
    If TextBox14 > 30 Then
    bestandnaam3 = TextBox16 & TextBox17 & "-meten" & ".dwg"
    Kill (bestandnaam3)
End If

Unload Me
End Sub
Private Sub cmdAfsluiten_Click()

If TextBox18 <> "" Then
 checkopexport = Split(TextBox18, ".")
 checkopexport1 = Right(checkopexport(0), 5)
 If checkopexport1 = "meten" Then ThisDrawing.Close
 bestandnaam3 = TextBox16 & TextBox17 & "-meten" & ".dwg"
 Kill (bestandnaam3)
End If

Unload Me
End Sub
Sub extreemtek()

TextBox14 = Clear
For Each layerObj In ThisDrawing.Layers
     If Left(layerObj.Name, 5) = "groep" Then TextBox14 = (Val(TextBox14)) + 1  'aantal groepen
Next 'layerobj
If TextBox14 = "" Then TextBox14 = 0

For Each element2 In ThisDrawing.ModelSpace
      If element2.ObjectName = "AcDbBlockReference" Then
      If UCase(element2.Name) = "KADERLOGO" Or UCase(element2.Name) = "LOGOTGH" Then
      Set symbool = element2
        If symbool.HasAttributes Then
        attributen = symbool.GetAttributes
        For k = LBound(attributen) To UBound(attributen)
        Set attribuut = attributen(k)
        If attribuut.TagString = "SCHAAL" Then schaalfaktor = attribuut.textstring
        Next k
       
      End If
      End If
      End If
Next element2

vartab = ThisDrawing.GetVariable("EXTMAX")

' A3 T/M A0+
If vartab(0) >= 2045 And vartab(0) <= 2055 Or vartab(0) >= 2915 And vartab(0) <= 2925 _
    Or vartab(0) >= 4175 And vartab(0) <= 4185 Or vartab(0) >= 5890 And vartab(0) <= 5900 _
    Or vartab(0) >= 7840 And vartab(0) <= 7850 Then
    maxwaarde = 1
Else
    maxwaarde = 2
End If
If vartab(0) >= 16715 And vartab(0) <= 16725 Or vartab(0) >= 23575 And vartab(0) <= 23585 _
    Or vartab(0) >= 31375 And vartab(0) <= 31385 Then
    maxwaarde = 4
End If
Update

If schaalfaktor = "1:50" And maxwaarde = 1 Then scaal = 1
If schaalfaktor = "1:100" And maxwaarde = 1 Then scaal = 2
If schaalfaktor = "1:200" And maxwaarde = 1 Then scaal = 4

If schaalfaktor = "1:50" And maxwaarde = 2 Then scaal = 0.5
If schaalfaktor = "1:100" And maxwaarde = 2 Then scaal = 1
If schaalfaktor = "1:200" And maxwaarde = 2 Then scaal = 2

If schaalfaktor = "1:200" And maxwaarde = 4 Then scaal = 1
TextBox19.Value = scaal

teknaam = ThisDrawing.GetVariable("dwgname")    'teknaam = ThisDrawing.GetVariable("dwgname")
TextBox15 = teknaam
TextBox16 = "c:\acad2002\"  'pad = ThisDrawing.GetVariable("dwgprefix")
teknaam1 = Split(teknaam, ("."))                'teknaam1 = Split(teknaam, ("."))

         Dim mystr As Variant
         mystr = Len(teknaam)
         over = mystr - 4 'aantal karakters
         teknaam6 = Left(teknaam, over)

'TextBox18 = teknaam1(0)
TextBox17 = teknaam6


'aantal groepen groter dan 30 ????
If TextBox14 > 30 Then
Call exportuserr2
frmInregelstaat.Hide

 
'bestandnaam2 = pad & teknaam1(0) & "-export" & ".dwg"
bestandnaam2 = TextBox16 & TextBox17 & "-meten" & ".dwg"
TextBox18 = bestandnaam2

'Kill (bestandnaam)
'Call zoekblad(bladnummer)

ThisDrawing.SendCommand "-layer" & vbCr & "unlock" & vbCr & "*" & vbCr & vbCr
ThisDrawing.SendCommand "-layer" & vbCr & "set" & vbCr & "0" & vbCr & vbCr
ThisDrawing.SendCommand "-layer" & vbCr & "Freeze" & vbCr & "*" & vbCr & vbCr
ThisDrawing.SendCommand "-layer" & vbCr & "Thaw" & vbCr & "groep*" & vbCr & vbCr
ThisDrawing.SendCommand "-layer" & vbCr & "Thaw" & vbCr & "gt" & vbCr & vbCr

ThisDrawing.SendCommand "_copyclip" & vbCr & "all" & vbCr & vbCr
ThisDrawing.SendCommand "-layer" & vbCr & "Thaw" & vbCr & "*" & vbCr & vbCr

templatenaam = ThisDrawing.GetVariable("acadver")
If templatenaam = "15.06s (LMS Tech)" Then ThisDrawing.Application.Documents.Add ("acad2000.dwt")
If templatenaam >= "16.0s (LMS Tech)" Then ThisDrawing.Application.Documents.Add ("autocad.dwt")

ThisDrawing.SendCommand "_pasteclip" & vbCr & "0,0" & vbCr

ThisDrawing.SaveAs (bestandnaam2)

End If

ZoomExtents


End Sub

Attribute VB_Name = "frmKaderlogo"
Attribute VB_Base = "0{3EE1C291-C6AB-4A44-9E85-A4BCF426F04A}{018A413E-C17B-4A6F-A2DF-0BBCA6F2121F}"
Attribute VB_GlobalNameSpace = False
Attribute VB_Creatable = False
Attribute VB_PredeclaredId = True
Attribute VB_Exposed = False
Attribute VB_TemplateDerived = False
Attribute VB_Customizable = False
'29-09-2003 Plaatsen van Kaderlogo
'M.Bosch en G.C.Haak
'kruisje uitschakelen
'G:\TEKENINGEN\ACAD2002\DWG\kaderlogo.dwg
#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
Dim blockObj As AcadBlock
Call Check_Kaderlogo.Check_Kaderlogo
 
 
 For Each element12 In ThisDrawing.ModelSpace
      If element12.ObjectName = "AcDbBlockReference" Then
        If element12.Name = "KaderlogoEngels" Then
        CheckBox9.Value = True
        CheckBox9.Enabled = False
        CheckBox10.Value = True
        End If
       End If
 Next element12


If ToggleButton1.Value = False Then ToggleButton1.Accelerator = "W"
frmKaderlogo.Width = 370
TextBox1.SetFocus
Call combolijst1
Call Schaal(scaal)
If scaal = 2 Then
schaalv = "1:100"
Else
schaalv = "1:50"
End If
If scaal = 4 Then schaalv = "1:200"


Call loginnaam(lognaam) 'Loginnaam oproepen
Call datum(kdate)


Dim element As Object
For Each element In ThisDrawing.ModelSpace
      If element.ObjectName = "AcDbBlockReference" Then
      If element.Name = "Kaderlogo" Or element.Name = "logotgh" Then
      Set symbool = element
        If symbool.HasAttributes Then
        attributen = symbool.GetAttributes
        For I = LBound(attributen) To UBound(attributen)
        Set attribuut = attributen(I)
        If attribuut.TagString = "OPDRACHTGEVER" Then TextBox1 = attribuut.textstring
        If attribuut.TagString = "PLAATS" Then TextBox2 = attribuut.textstring
        'If attribuut.TagString = "PROJECTNAAM" Then TextBox3 = StrConv(attribuut.TextString, vbProperCase)
        'If attribuut.TagString = "MONTAGEADRES" Then TextBox4 = StrConv(attribuut.TextString, vbProperCase)
        'If attribuut.TagString = "MONTAGEPLAATS" Then TextBox5 = StrConv(attribuut.TextString, vbProperCase)
        If attribuut.TagString = "PROJECTNAAM" Then TextBox3 = attribuut.textstring
        If attribuut.TagString = "MONTAGEADRES" Then TextBox4 = attribuut.textstring
        If attribuut.TagString = "MONTAGEPLAATS" Then TextBox5 = attribuut.textstring
        If attribuut.TagString = "PROJECTNUMMER" Then TextBox6 = Left(ThisDrawing.GetVariable("dwgname"), 9) 'attribuut.TextString
        If attribuut.TagString = "BLAD" Then ComboBox1 = attribuut.textstring
        If attribuut.TagString = "BLAD" And attribuut.textstring = "" Then ComboBox1 = "1"
        If attribuut.TagString = "FORMAAT" Then TextBox8 = attribuut.textstring
        If attribuut.TagString = "TEKENAAR" And attribuut.textstring = "" Then TextBox9 = lognaam
        If attribuut.TagString = "TEKENAAR" And attribuut.textstring <> "" Then TextBox9 = attribuut.textstring
        If attribuut.TagString = "SCHAAL" And attribuut.textstring = "" Then TextBox10 = schaalv
        If attribuut.TagString = "SCHAAL" And attribuut.textstring <> "" Then TextBox10 = attribuut.textstring
        If attribuut.TagString = "DATUM" And attribuut.textstring = "" Then TextBox11 = kdate ' & "|" & lognaam
        If attribuut.TagString = "DATUM" And attribuut.textstring <> "" Then TextBox11 = attribuut.textstring
        If attribuut.TagString = "WIJZIGING1" And attribuut.textstring <> "" Then TextBox12 = attribuut.textstring
        If attribuut.TagString = "WIJZIGING2" And attribuut.textstring <> "" Then TextBox13 = attribuut.textstring
        If attribuut.TagString = "WIJZIGING3" And attribuut.textstring <> "" Then TextBox14 = attribuut.textstring
        If attribuut.TagString = "WIJZIGING4" And attribuut.textstring <> "" Then TextBox15 = attribuut.textstring
        If attribuut.TagString = "WIJZIGING5" And attribuut.textstring <> "" Then TextBox16 = attribuut.textstring
        If attribuut.TagString = "WIJZIGING6" And attribuut.textstring <> "" Then TextBox17 = attribuut.textstring
        If attribuut.TagString = "WIJZIGING7" And attribuut.textstring <> "" Then TextBox18 = attribuut.textstring
        If attribuut.TagString = "REVISIE" And attribuut.textstring <> "" Then TextBox19 = attribuut.textstring
        Next I
       End If
     End If
   End If
  Next element
  
  Dim element1 As Object
For Each element1 In ThisDrawing.ModelSpace
      If element1.ObjectName = "AcDbBlockReference" Then
      If element1.Name = "KaderlogoEngels" Then
      Set symbool = element1
        If symbool.HasAttributes Then
        attributen = symbool.GetAttributes
        For I = LBound(attributen) To UBound(attributen)
        Set attribuut = attributen(I)
        If attribuut.TagString = "OPDRACHTGEVER" Then TextBox1 = attribuut.textstring
        If attribuut.TagString = "PLAATS" Then TextBox2 = attribuut.textstring
        'If attribuut.TagString = "PROJECTNAAM" Then TextBox3 = StrConv(attribuut.TextString, vbProperCase)
        'If attribuut.TagString = "MONTAGEADRES" Then TextBox4 = StrConv(attribuut.TextString, vbProperCase)
        'If attribuut.TagString = "MONTAGEPLAATS" Then TextBox5 = StrConv(attribuut.TextString, vbProperCase)
        If attribuut.TagString = "PROJECTNAAM" Then TextBox3 = attribuut.textstring
        If attribuut.TagString = "MONTAGEADRES" Then TextBox4 = attribuut.textstring
        If attribuut.TagString = "MONTAGEPLAATS" Then TextBox5 = attribuut.textstring
        If attribuut.TagString = "PROJECTNUMMER" Then TextBox6 = Left(ThisDrawing.GetVariable("dwgname"), 9) 'attribuut.TextString
        If attribuut.TagString = "BLAD" Then ComboBox1 = attribuut.textstring
        If attribuut.TagString = "BLAD" And attribuut.textstring = "" Then ComboBox1 = "1"
        If attribuut.TagString = "FORMAAT" Then TextBox8 = attribuut.textstring
        If attribuut.TagString = "TEKENAAR" And attribuut.textstring = "" Then TextBox9 = lognaam
        If attribuut.TagString = "TEKENAAR" And attribuut.textstring <> "" Then TextBox9 = attribuut.textstring
        If attribuut.TagString = "SCHAAL" And attribuut.textstring = "" Then TextBox10 = schaalv
        If attribuut.TagString = "SCHAAL" And attribuut.textstring <> "" Then TextBox10 = attribuut.textstring
        If attribuut.TagString = "DATUM" And attribuut.textstring = "" Then TextBox11 = kdate ' & "|" & lognaam
        If attribuut.TagString = "DATUM" And attribuut.textstring <> "" Then TextBox11 = attribuut.textstring
        If attribuut.TagString = "WIJZIGING1" And attribuut.textstring <> "" Then TextBox12 = attribuut.textstring
        If attribuut.TagString = "WIJZIGING2" And attribuut.textstring <> "" Then TextBox13 = attribuut.textstring
        If attribuut.TagString = "WIJZIGING3" And attribuut.textstring <> "" Then TextBox14 = attribuut.textstring
        If attribuut.TagString = "WIJZIGING4" And attribuut.textstring <> "" Then TextBox15 = attribuut.textstring
        If attribuut.TagString = "WIJZIGING5" And attribuut.textstring <> "" Then TextBox16 = attribuut.textstring
        If attribuut.TagString = "WIJZIGING6" And attribuut.textstring <> "" Then TextBox17 = attribuut.textstring
        If attribuut.TagString = "WIJZIGING7" And attribuut.textstring <> "" Then TextBox18 = attribuut.textstring
        If attribuut.TagString = "REVISIE" And attribuut.textstring <> "" Then TextBox19 = attribuut.textstring
        Next I
       End If
     End If
   End If
  Next element1
  
  'If TextBox19 <> "" Then CheckBox1 = True
  'If TextBox12 <> "" Then CheckBox2 = True
  'If TextBox13 <> "" Then CheckBox3 = True
  'If TextBox14 <> "" Then CheckBox4 = True
  'If TextBox15 <> "" Then CheckBox5 = True
  'If TextBox16 <> "" Then CheckBox6 = True
  'If TextBox17 <> "" Then CheckBox7 = True
  'If TextBox18 <> "" Then CheckBox8 = True
  If TextBox12 <> "" Or TextBox13 <> "" Or TextBox14 <> "" Then frmKaderlogo.Width = 514
  If TextBox15 <> "" Or TextBox16 <> "" Or TextBox17 <> "" Or TextBox18 <> "" Then frmKaderlogo.Width = 514
If TextBox6.Value <> "" Then TextBox6.Locked = True
If TextBox8.Value <> "" Then TextBox8.Locked = True
'If TextBox9.Value <> "" Then TextBox9.Locked = True
If TextBox10.Value <> "" Then TextBox10.Locked = True
'If TextBox11.Value <> "" Then TextBox11.Locked = True
If frmKaderlogo.Width = 514 Then ToggleButton1.Value = True
Update

ToggleButton2.Picture = LoadPicture("c:\acad2002\dwg\engeland.bmp")
ToggleButton2.ControlTipText = "Omschakelen naar engels"

lognaam = ThisDrawing.GetVariable("loginname")
lognaam = UCase(lognaam)

If lognaam = "GERARD" Then frmKaderlogo.StartUpPosition = 0
End Sub
Sub datum(kdate)
datumacad1 = ThisDrawing.GetVariable("cdate")
datumacad = Left(datumacad1, 8)
'datumacad = 20040604
dag = Right(datumacad, 2)
maand = Left(datumacad, 6)
maand2 = Right(maand, 2)
jaar = Left(datumacad, 4)

kdate = dag & "-" & maand2 & "-" & jaar

End Sub
Private Sub CheckBox2_Click()
Call loginnaam(lognaam)
Call datum(kdate)
If CheckBox2.Value = True Then
TextBox12 = kdate & "|" & lognaam
Else
TextBox12 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub

Private Sub CheckBox3_Click()
Call loginnaam(lognaam)
Call datum(kdate)
If CheckBox3.Value = True Then
TextBox13 = kdate & "|" & lognaam
Else
TextBox13 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub

Private Sub CheckBox4_Click()
Call loginnaam(lognaam)
Call datum(kdate)
If CheckBox4.Value = True Then
TextBox14 = kdate & "|" & lognaam
Else
TextBox14 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub
Private Sub CheckBox5_Click()
Call loginnaam(lognaam)
Call datum(kdate)
If CheckBox5.Value = True Then
TextBox15 = kdate & "|" & lognaam
Else
TextBox15 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub
Private Sub CheckBox6_Click()
Call loginnaam(lognaam)
Call datum(kdate)
If CheckBox6.Value = True Then
TextBox16 = kdate & "|" & lognaam
Else
TextBox16 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub
Private Sub CheckBox7_Click()
Call loginnaam(lognaam)
Call datum(kdate)
If CheckBox7.Value = True Then
TextBox17 = kdate & "|" & lognaam
Else
TextBox17 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub
Private Sub CheckBox8_Click()
Call loginnaam(lognaam)
Call datum(kdate)
If CheckBox8.Value = True Then
TextBox18 = kdate & "|" & lognaam
Else
TextBox18 = ""
End If
If TextBox12 = "" And TextBox13 = "" And TextBox14 = "" And TextBox15 = "" _
And TextBox15 = "" And TextBox16 = "" And TextBox17 = "" And TextBox18 = "" Then
frmKaderlogo.Width = 370
ToggleButton1 = False
End If
End Sub
Private Sub Logoplaats_Click()
On Error Resume Next
Call Schaal(scaal)

Dim pb3 As Variant
frmKaderlogo.Hide
    Set newLayer = ThisDrawing.Layers.Add("LOGO")
    ThisDrawing.ActiveLayer = newLayer
    Update
    ThisDrawing.SendCommand "-layer" & vbCr & "U" & vbCr & "LOGO" & vbCr & vbCr
    ThisDrawing.SendCommand "-layer" & vbCr & "U" & vbCr & "GT" & vbCr & vbCr
    ThisDrawing.SendCommand "osmode" & vbCr & "1" & vbCr
    Update
pb3 = ThisDrawing.Utility.GetPoint(, "Plaats beginpunt...")
Dim bestand As String
bestand = "G:\tekeningen\ACAD2002\DWG\kaderlogo.dwg"
  Set blockRefObj = ThisDrawing.ModelSpace.InsertBlock(pb3, bestand, scaal, scaal, 1, 0)

If Err Then
    ThisDrawing.SendCommand "osmode" & vbCr & "0" & vbCr
    frmKaderlogo.Show
    Exit Sub
    End If

Dim element As Object
For Each element In ThisDrawing.ModelSpace
      If element.ObjectName = "AcDbBlockReference" Then
      If element.Name = "Kaderlogo" Then
      Set symbool = element
        If symbool.HasAttributes Then
        attributen = symbool.GetAttributes
        For I = LBound(attributen) To UBound(attributen)
        Set attribuut = attributen(I)
        If attribuut.TagString = "OPDRACHTGEVER" Then attribuut.textstring = TextBox1
        If attribuut.TagString = "PLAATS" Then attribuut.textstring = TextBox2
        If attribuut.TagString = "PROJECTNAAM" Then attribuut.textstring = TextBox3
        If attribuut.TagString = "MONTAGEADRES" Then attribuut.textstring = TextBox4
        If attribuut.TagString = "MONTAGEPLAATS" Then attribuut.textstring = TextBox5
        If attribuut.TagString = "PROJECTNUMMER" Then attribuut.textstring = TextBox6
        If attribuut.TagString = "BLAD" Then attribuut.textstring = ComboBox1
        If attribuut.TagString = "FORMAAT" Then attribuut.textstring = TextBox8
        If attribuut.TagString = "TEKENAAR" Then attribuut.textstring = TextBox9
        If attribuut.TagString = "SCHAAL" Then attribuut.textstring = TextBox10
        If attribuut.TagString = "DATUM" Then attribuut.textstring = TextBox11
        'If attribuut.TagString = "WIJZIGING1" Then attribuut.TextString = TextBox12
       Next I
      End If
      End If
      End If
  Next element
  Update
End Sub
Private Sub CheckBox1_Click()
Call loginnaam(lognaam)
Call datum(kdate)
If CheckBox1.Value = True Then
TextBox19 = kdate & "|" & lognaam
Else
TextBox19 = ""
End If
End Sub
Private Sub TextBox10_Change()
If TextBox10.Value <> "" Then TextBox10.Locked = True
End Sub
Private Sub TextBox1_DblClick(ByVal Cancel As MSForms.ReturnBoolean)
TextBox1 = ""
End Sub
Private Sub TextBox2_DblClick(ByVal Cancel As MSForms.ReturnBoolean)
TextBox2 = ""
End Sub
Private Sub TextBox3_DblClick(ByVal Cancel As MSForms.ReturnBoolean)
TextBox3 = ""
End Sub
Private Sub TextBox4_DblClick(ByVal Cancel As MSForms.ReturnBoolean)
TextBox4 = ""
End Sub
Private Sub TextBox5_DblClick(ByVal Cancel As MSForms.ReturnBoolean)
TextBox5 = ""
End Sub
Private Sub CmdUpdate_Click()
Grootklein = Left(ThisDrawing.GetVariable("dwgname"), 2) 'nummer checken
'Call Schaal(scaal)
'frmKaderlogo.Show
scaal = frmKaderlogo.TextBox20



Dim bestand90 As String
bestand90 = "C:\ACAD2002\DWG\KaderlogoEngels.dwg"

If CheckBox9 = True And CheckBox10 = False Then
  'Dim element As Object
  'Dim layerObj As AcadLayer
  'Kaderlogo verwijderen
     For Each element In ThisDrawing.ModelSpace
      If element.ObjectName = "AcDbBlockReference" Then
         If element.Name = "Kaderlogo" Then
          engkaderlogo = element.InsertionPoint
          element.Erase
          Set blockRefObj = ThisDrawing.ModelSpace.InsertBlock(engkaderlogo, bestand90, scaal, scaal, 1, 0)
         End If
      Update
      End If
     Next element
     
 End If

''Dim element10 As Object
'If CheckBox9.Value = False Then
     For Each element10 In ThisDrawing.ModelSpace
      If element10.ObjectName = "AcDbBlockReference" Then
      If element10.Name = "Kaderlogo" Or element10.Name = "KaderlogoEngels" Or element10.Name = "logotgh" Then
      Set symbool = element10
        If symbool.HasAttributes Then
        attributen = symbool.GetAttributes
        For I = LBound(attributen) To UBound(attributen)
        Set attribuut = attributen(I)
        If attribuut.TagString = "OPDRACHTGEVER" Then attribuut.textstring = TextBox1
        If attribuut.TagString = "PLAATS" Then attribuut.textstring = UCase(TextBox2)
        If attribuut.TagString = "PROJECTNAAM" Then attribuut.textstring = TextBox3
        If attribuut.TagString = "MONTAGEADRES" Then attribuut.textstring = TextBox4
        If attribuut.TagString = "MONTAGEPLAATS" Then attribuut.textstring = TextBox5
        If attribuut.TagString = "PROJECTNUMMER" And Grootklein = "p0" Then attribuut.textstring = LCase(TextBox6)
        If attribuut.TagString = "PROJECTNUMMER" And Grootklein <> "p0" Then attribuut.textstring = UCase(TextBox6)
        If attribuut.TagString = "BLAD" Then attribuut.textstring = ComboBox1
        If attribuut.TagString = "FORMAAT" Then attribuut.textstring = TextBox8
        If attribuut.TagString = "TEKENAAR" Then attribuut.textstring = TextBox9
        If attribuut.TagString = "SCHAAL" Then attribuut.textstring = TextBox10
        If attribuut.TagString = "DATUM" Then attribuut.textstring = TextBox11
        If attribuut.TagString = "WIJZIGING1" Then attribuut.textstring = TextBox12
        If attribuut.TagString = "WIJZIGING2" Then attribuut.textstring = TextBox13
        If attribuut.TagString = "WIJZIGING3" Then attribuut.textstring = TextBox14
        If attribuut.TagString = "WIJZIGING4" Then attribuut.textstring = TextBox15
        If attribuut.TagString = "WIJZIGING5" Then attribuut.textstring = TextBox16
        If attribuut.TagString = "WIJZIGING6" Then attribuut.textstring = TextBox17
        If attribuut.TagString = "WIJZIGING7" Then attribuut.textstring = TextBox18
        If attribuut.TagString = "REVISIE" Then attribuut.textstring = TextBox19
       Next I

      End If
      End If
      End If
      Next element10
'End If
'CheckBox10.Value = True
Update

Dim bestand92 As String
bestand92 = "C:\ACAD2002\DWG\bl-revisie.dwg"
  If CheckBox1.Value = True Then
   For Each element In ThisDrawing.ModelSpace
      If element.ObjectName = "AcDbBlockReference" Then
         If element.Name = "definitief" Or element.Name = "definitief2" Or _
         element.Name = "voorlopig" Or element.Name = "goedkeuring" Or element.Name = "uitvoering" Then
          insp = element.InsertionPoint
          element.Erase
          Set blockRefObj = ThisDrawing.ModelSpace.InsertBlock(insp, bestand92, scaal, scaal, 1, 0)
         End If
       Update
      End If
     Next element
   End If 'checkbox

End Sub
Private Sub cmdAfsluiten_Click()
If Left(UCase(frmKaderlogo.TextBox1), 7) = "LOOHUIS" And UCase(frmKaderlogo.TextBox2) = "SAASVELD" Then MsgBox "DENK AAN DE MONTAGEBLOKKEN", vbExclamation
Unload Me
'lvblokken
End Sub
Sub Schaal(scaal)
frmKaderlogo.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
TextBox20 = scaal
Update
End Sub
Sub loginnaam(lognaam)

lognaam = ThisDrawing.GetVariable("loginname")
lognaam = UCase(lognaam)
If lognaam = "DBRUI" Then lognaam = "DdB"
If lognaam = "WPORS" Then lognaam = "WP"
If lognaam = "JMASI" Then lognaam = "JM"
If lognaam = "GERARD" Then lognaam = "GCH"
If lognaam = "ILONA" Then lognaam = "IK"
If lognaam = "BJORN" Then lognaam = "BC"
If lognaam = "DENNIS" Then lognaam = "DvdW"
If lognaam = "ZILVERSCHOONJ" Then lognaam = "JZ"
If lognaam = "BGOUW" Then lognaam = "BG"
If lognaam = "OYILM" Then lognaam = "OY"
If lognaam = "SNABI" Then lognaam = "SN"
If lognaam = "DLALI" Then lognaam = "DL"
If lognaam = "GLUII" Then lognaam = "GL"
If lognaam = "DWILS" Then lognaam = "DW"
If lognaam = "JPRINS" Then lognaam = "JP"
End Sub
Sub combolijst1()

ComboBox1.AddItem "1"
ComboBox1.AddItem "W00"
ComboBox1.AddItem "W01"
ComboBox1.AddItem "W02"
ComboBox1.AddItem "W03"
ComboBox1.AddItem "W04"
ComboBox1.AddItem "W05"
ComboBox1.AddItem "W06"
ComboBox1.AddItem "W07"
ComboBox1.AddItem "W08"
ComboBox1.ListIndex = 0
ComboBox1.MatchEntry = fmMatchEntryFirstLetter

End Sub
Private Sub CommandButton1_Click()
'TextBox3 = StrConv(TextBox3, vbProperCase)
'TextBox4 = StrConv(TextBox4, vbProperCase)
'TextBox5 = StrConv(TextBox5, vbProperCase)

Grootklein = Left(ThisDrawing.GetVariable("dwgname"), 2) 'nummer checken

Dim element10 As Object
If CheckBox9.Value = False Then
     For Each element10 In ThisDrawing.ModelSpace
      If element10.ObjectName = "AcDbBlockReference" Then
      If element10.Name = "Kaderlogo" And CheckBox9.Value = False Then
      Set symbool = element10
        If symbool.HasAttributes Then
        attributen = symbool.GetAttributes
        For I = LBound(attributen) To UBound(attributen)
        Set attribuut = attributen(I)
        If attribuut.TagString = "OPDRACHTGEVER" Then attribuut.textstring = TextBox1
        If attribuut.TagString = "PLAATS" Then attribuut.textstring = UCase(TextBox2)
        If attribuut.TagString = "PROJECTNAAM" Then attribuut.textstring = TextBox3
        If attribuut.TagString = "MONTAGEADRES" Then attribuut.textstring = TextBox4
        If attribuut.TagString = "MONTAGEPLAATS" Then attribuut.textstring = TextBox5
        If attribuut.TagString = "PROJECTNUMMER" And Grootklein = "p0" Then attribuut.textstring = LCase(TextBox6)
        If attribuut.TagString = "PROJECTNUMMER" And Grootklein <> "p0" Then attribuut.textstring = UCase(TextBox6)
        If attribuut.TagString = "BLAD" Then attribuut.textstring = ComboBox1
        If attribuut.TagString = "FORMAAT" Then attribuut.textstring = TextBox8
        If attribuut.TagString = "TEKENAAR" Then attribuut.textstring = TextBox9
        If attribuut.TagString = "SCHAAL" Then attribuut.textstring = TextBox10
        If attribuut.TagString = "DATUM" Then attribuut.textstring = TextBox11
        If attribuut.TagString = "WIJZIGING1" Then attribuut.textstring = TextBox12
        If attribuut.TagString = "WIJZIGING2" Then attribuut.textstring = TextBox13
        If attribuut.TagString = "WIJZIGING3" Then attribuut.textstring = TextBox14
        If attribuut.TagString = "WIJZIGING4" Then attribuut.textstring = TextBox15
        If attribuut.TagString = "WIJZIGING5" Then attribuut.textstring = TextBox16
        If attribuut.TagString = "WIJZIGING6" Then attribuut.textstring = TextBox17
        If attribuut.TagString = "WIJZIGING7" Then attribuut.textstring = TextBox18
        If attribuut.TagString = "REVISIE" Then attribuut.textstring = TextBox19
       Next I

      End If
      End If
      End If
      Next element10
End If
'Else


 ' For Each GG In ThisDrawing.ModelSpace
 '   If GG.ObjectName = "AcDbBlockReference" Then
 '      If GG.Name = "Kaderlogo" Then
 '         a = GG.InsertionPoint
 '         'GG.Delete
          'Set blockRefObj = ThisDrawing.ModelSpace.InsertBlock(a, "C:\ACAD2002\DWG\bl-bouw.dwg", 1, 1, 1, 0)
 '       End If
 '   End If
 ' Next


If CheckBox9 = True And CheckBox10 = False Then
Dim element As Object
Dim layerObj As AcadLayer
'Kaderlogo verwijderen
     For Each element In ThisDrawing.ModelSpace
      If element.ObjectName = "AcDbBlockReference" Then
         If element.Name = "Kaderlogo" Then
          engkaderlogo = element.InsertionPoint
          element.Erase
         End If
      Update
      End If
     Next element

         
         On Error Resume Next
         For Each element In ThisDrawing.ModelSpace
         If element.ObjectName = "AcDbBlockReference" Then
         If element.Name <> "KaderlogoEngels" Then
         
         
    If Err Then
    CheckBox10.Value = False
    frmKaderlogo.Show
    Exit Sub
    End If
          
         Dim bestand91 As String
         bestand91 = "C:\ACAD2002\DWG\KaderlogoEngels.dwg"
         Set blockRefObj = ThisDrawing.ModelSpace.InsertBlock(engkaderlogo, bestand91, 1, 1, 1, 0)
         End If
         End If
         Next element
         Update
         CheckBox10 = True
End If



Dim element11 As Object
For Each element11 In ThisDrawing.ModelSpace
     If element11.ObjectName = "AcDbBlockReference" Then
      If element11.Name = "KaderlogoEngels" And CheckBox9.Value = True Then
      Set symbool = element11
        If symbool.HasAttributes Then
        attributen = symbool.GetAttributes
        For I = LBound(attributen) To UBound(attributen)
        Set attribuut = attributen(I)
        If attribuut.TagString = "OPDRACHTGEVER" Then attribuut.textstring = TextBox1
        If attribuut.TagString = "PLAATS" Then attribuut.textstring = UCase(TextBox2)
        If attribuut.TagString = "PROJECTNAAM" Then attribuut.textstring = TextBox3
        If attribuut.TagString = "MONTAGEADRES" Then attribuut.textstring = TextBox4
        If attribuut.TagString = "MONTAGEPLAATS" Then attribuut.textstring = TextBox5
        If attribuut.TagString = "PROJECTNUMMER" And Grootklein = "p0" Then attribuut.textstring = LCase(TextBox6)
        If attribuut.TagString = "PROJECTNUMMER" And Grootklein <> "p0" Then attribuut.textstring = UCase(TextBox6)
        If attribuut.TagString = "BLAD" Then attribuut.textstring = ComboBox1
        If attribuut.TagString = "FORMAAT" Then attribuut.textstring = TextBox8
        If attribuut.TagString = "TEKENAAR" Then attribuut.textstring = TextBox9
        If attribuut.TagString = "SCHAAL" Then attribuut.textstring = TextBox10
        If attribuut.TagString = "DATUM" Then attribuut.textstring = TextBox11
        If attribuut.TagString = "WIJZIGING1" Then attribuut.textstring = TextBox12
        If attribuut.TagString = "WIJZIGING2" Then attribuut.textstring = TextBox13
        If attribuut.TagString = "WIJZIGING3" Then attribuut.textstring = TextBox14
        If attribuut.TagString = "WIJZIGING4" Then attribuut.textstring = TextBox15
        If attribuut.TagString = "WIJZIGING5" Then attribuut.textstring = TextBox16
        If attribuut.TagString = "WIJZIGING6" Then attribuut.textstring = TextBox17
        If attribuut.TagString = "WIJZIGING7" Then attribuut.textstring = TextBox18
        If attribuut.TagString = "REVISIE" Then attribuut.textstring = TextBox19
        
       Next I
       
       
       
        End If
      End If
    End If
Next element11
'End If
'End If 'checkbox9
Update


End Sub
Private Sub ToggleButton1_Click()
If ToggleButton1 = True Then frmKaderlogo.Width = 514
If ToggleButton1 = False Then frmKaderlogo.Width = 370

If ToggleButton2.Value = False Then
        If ToggleButton1 = True Then
        ToggleButton1.Caption = "Geen Wijz."
        ToggleButton1.Accelerator = "W"
        Else
        ToggleButton1.Caption = "Wijzigen."
        ToggleButton1.Accelerator = "W"
        End If
End If
If ToggleButton2.Value = True Then
        If ToggleButton1 = True Then
        ToggleButton1.Caption = "No Alteration"
        ToggleButton1.Accelerator = "N"
        Else
        ToggleButton1.Caption = "Alteration"
        ToggleButton1.Accelerator = "A"
        End If
End If
End Sub

Private Sub ToggleButton2_Click()
If ToggleButton2.Value = False Then
   If ToggleButton1 = True Then
        ToggleButton1.Caption = "Geen Wijz."
        ToggleButton1.Accelerator = "W"
        Else
        ToggleButton1.Caption = "Wijzigen."
        ToggleButton1.Accelerator = "W"
        End If
   ToggleButton2.Picture = LoadPicture("c:\acad2002\dwg\engeland.bmp")
   ToggleButton2.ControlTipText = "Omschakelen naar engels"
   Call togglemodule.kaderlogo_dutch
   End If
If ToggleButton2.Value = True Then
        If ToggleButton1 = True Then
        ToggleButton1.Caption = "No Alteration"
        ToggleButton1.Accelerator = "N"
        Else
        ToggleButton1.Caption = "Alteration"
        ToggleButton1.Accelerator = "A"
        End If
   ToggleButton2.Picture = LoadPicture("c:\acad2002\dwg\nederland.bmp")
   ToggleButton2.ControlTipText = "Switch to Dutch"
   Call togglemodule.kaderlogo_english
   End If
End Sub

Attribute VB_Name = "frmLegrichtingFF"
Attribute VB_Base = "0{3C7A26D6-B6EE-4E9A-A59C-6DDAEA80D7BE}{3D5EAF31-218B-4C2D-8CCB-CA66F1EBB1F6}"
Attribute VB_GlobalNameSpace = False
Attribute VB_Creatable = False
Attribute VB_PredeclaredId = True
Attribute VB_Exposed = False
Attribute VB_TemplateDerived = False
Attribute VB_Customizable = False
'09-09-2005 Legrichting bepalen
'M.Bosch en G.C.Haak
#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If

box1 = ThisDrawing.GetVariable("angdir")

If box1 = 0 Then OptionButton1.Value = True
If box1 = 1 Then OptionButton2.Value = True
End Sub
Private Sub cmdAfsluiten_Click()
If OptionButton1.Value = True Then ThisDrawing.SetVariable "angdir", 0
If OptionButton2.Value = True Then ThisDrawing.SetVariable "angdir", 1
Unload Me
End Sub

Attribute VB_Name = "frmUnitlogo"
Attribute VB_Base = "0{0DD2A778-AA8D-4D74-AE77-B9CAD4495F71}{31672691-7A1F-40AC-9980-026774384272}"
Attribute VB_GlobalNameSpace = False
Attribute VB_Creatable = False
Attribute VB_PredeclaredId = True
Attribute VB_Exposed = False
Attribute VB_TemplateDerived = False
Attribute VB_Customizable = False

'19-08-2003
'M.Bosch en G.C.Haak
'BESTANDEN:
'unitlogo_wthzd.dwg
'unitlogo_pert.dwg
'unitlogo_alu.dwg
'unitlogo_extragroepen


#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000

Private Sub CheckBox4_Click()
If CheckBox4.Value = False Then TextBox70 = "0"
End Sub
Private Sub CheckBox5_Click()
If CheckBox5.Value = False Then TextBox71 = "0"
End Sub

Private Sub TextBox70_Change()
If frmUnitlogo.TextBox70 <> "0" Then frmUnitlogo.CheckBox4 = True
End Sub

Private Sub TextBox71_Change()
If frmUnitlogo.TextBox71 <> "0" Then CheckBox5.Value = True
End Sub

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
 frmUnitlogo.Height = 250 '282
 'frmUnitlogo.Width = 698
 Label28.Caption = Clear: Label30.Caption = Clear
 Label25.Caption = Clear: Label29.Caption = Clear
 Label34.Caption = Clear
TextBox1.SetFocus


Dim lognaam
lognaam = ThisDrawing.GetVariable("loginname")
lognaam = UCase(lognaam)
If lognaam = "GERARD" Then
    CheckBox2.Visible = True
    CommandButton1.SetFocus
'    CheckBox3.Visible = True
End If

End Sub
Private Sub cmdschets_Click()
On Error Resume Next
Call Schaal(scaal)
ThisDrawing.SetVariable "osmode", 1
frmUnitlogo.Hide


Dim PBEGIN(0 To 2) As Double
For Each element In ThisDrawing.ModelSpace
      If element.ObjectName = "AcDbBlockReference" Then
         If element.Name = "Kaderlogo" Or element.Name = "ENG-Kaderlogo" Then
          insp = element.InsertionPoint
          PBEGIN(0) = insp(0) - (940 * scaal)
          PBEGIN(1) = insp(1) + (298.7 * scaal)
          PBEGIN(2) = insp(2)
          End If
      Update
      End If
     Next element


'PBEGIN = ThisDrawing.Utility.GetPoint(, "Plaats beginpunt -Materiaalstaat-")
Dim bestand93 As String
bestand93 = "C:\ACAD2002\DWG\unitlogo_WTHZD.dwg"
Set blockRefObj = ThisDrawing.ModelSpace.InsertBlock(PBEGIN, bestand93, scaal, scaal, 1, 0)

Dim pb3(0 To 2) As Double

 pb3(0) = PBEGIN(0)
 pb3(1) = PBEGIN(1) + (254.5 * scaal)
 pb3(2) = 0

 Dim bestand94 As String
bestand94 = "C:\ACAD2002\DWG\bl-krimp.dwg"
Set blockRefObj = ThisDrawing.ModelSpace.InsertBlock(pb3, bestand94, scaal, scaal, 1, 0)
If Err Then
    frmUnitlogo.Show
    Exit Sub
    End If
ThisDrawing.SetVariable "osmode", 0
End Sub

Private Sub CommandButton1_Click()
Call invullen
If CheckBox1.Value = True Then frmUnitlogo.Width = 780
If TextBox40 <> "0" Or TextBox46 <> "0" Or TextBox50 <> "0" Or TextBox54 <> "0" Or TextBox55 <> "0" _
Or TextBox56 <> "0" Or TextBox60 <> "0" Or TextBox69 <> "0" Or TextBox70 <> "0" Or TextBox71 <> "0" Then
Logoplaats.Enabled = True
cmdschets.Enabled = False
Else
Logoplaats.Enabled = False
cmdschets.Enabled = True
End If

If Label51 = "PE-RT16" Then Frame6.Enabled = False

Dim lognaam
lognaam = ThisDrawing.GetVariable("loginname")
lognaam = UCase(lognaam)
If lognaam = "GERARD" And CheckBox2.Value = True Then
    Call Logoplaats_Click
End If

End Sub
Sub invullen()
On Error Resume Next
Dim element As Object
a = 0
b = 0
grtwaarde = 0
'----WTH-ZD-----20 * 3,4 ------------------------------------------------------
For Each element In ThisDrawing.ModelSpace
      If element.ObjectName = "AcDbBlockReference" Then
      If element.Name = "Mat_spe_ZD" Or element.Name = "Mat_spe_ZDringleiding" Then
      Set symbool = element
      b = b + 1
        If symbool.HasAttributes Then
        attributen = symbool.GetAttributes
        For j = LBound(attributen) To UBound(attributen)
        Set attribuut = attributen(j)

        If attribuut.TagString = "RNU" Then a = attribuut.textstring
        If a > 10 Then grtwaarde = 1
        If a > 16 Then message = 1
        
        If attribuut.TagString = "WTH250" And attribuut.textstring <> "" Then _
        TextBox17 = TextBox17 + (Val(attribuut.textstring))  '250 METER
        If attribuut.TagString = "WTH165" And attribuut.textstring <> "" Then _
        TextBox18 = TextBox18 + (Val(attribuut.textstring))  '165 METER
        If attribuut.TagString = "WTH125" And attribuut.textstring <> "" Then _
        TextBox19 = TextBox19 + (Val(attribuut.textstring))  '125 METER
        If attribuut.TagString = "WTH105" And attribuut.textstring <> "" Then _
        TextBox20 = TextBox20 + (Val(attribuut.textstring))  '105 METER
        If attribuut.TagString = "WTH90" And attribuut.textstring <> "" Then _
        TextBox21 = TextBox21 + (Val(attribuut.textstring))  '90 METER
        If attribuut.TagString = "WTH75" And attribuut.textstring <> "" Then _
        TextBox22 = TextBox22 + (Val(attribuut.textstring))  '75 METER
        If attribuut.TagString = "WTH63" And attribuut.textstring <> "" Then _
        TextBox23 = TextBox23 + (Val(attribuut.textstring))  '63 METER
        If attribuut.TagString = "WTH50" And attribuut.textstring <> "" Then _
        TextBox41 = TextBox41 + (Val(attribuut.textstring)) '50 METER
        If attribuut.TagString = "WTH40" And attribuut.textstring <> "" Then _
        TextBox42 = TextBox42 + (Val(attribuut.textstring))   '40 METER
        If attribuut.TagString = "WTHZD" Then
         Label50 = "WTH-ZD"
         'Label30 = "ZD"
        End If
        
     
        Next j
       
        End If
      End If
      End If
  Next element


'----WTH-ZD--16 * 2,7--+ 500 meter rollen werkelijke lengte -------------------------------------------------------
For Each element In ThisDrawing.ModelSpace
      If element.ObjectName = "AcDbBlockReference" Then
      If element.Name = "Mat_spe_ZD_1627" Or element.Name = "Mat_spe_ZD_1627500" Then
      Set symbool = element
      b = b + 1
        If symbool.HasAttributes Then
        attributen = symbool.GetAttributes
        For j = LBound(attributen) To UBound(attributen)
        Set attribuut = attributen(j)

        If attribuut.TagString = "RNU" Then a = attribuut.textstring
        If a > 10 Then grtwaarde = 1
        If a > 16 Then message = 1
        
        If attribuut.TagString = "WTH105" And attribuut.textstring <> "" Then _
        TextBox65 = TextBox65 + (Val(attribuut.textstring))  '105 METER
        If attribuut.TagString = "WTH90" And attribuut.textstring <> "" Then _
        TextBox66 = TextBox66 + (Val(attribuut.textstring))  '90 METER
        If attribuut.TagString = "WTH75" And attribuut.textstring <> "" Then _
        TextBox67 = TextBox67 + (Val(attribuut.textstring))  '75 METER
        If attribuut.TagString = "WTH63" And attribuut.textstring <> "" Then _
        TextBox68 = TextBox68 + (Val(attribuut.textstring))  '63 METER
        
        If attribuut.TagString = "WTHZD" Then
         Label71 = "WTH-ZD_1627"
         'Label30 = "ZD"
        End If
               
        If attribuut.TagString = "LMETER" And attribuut.textstring <> "" Then C = attribuut.textstring
             
        Next j
        
        frmUnitlogo.TextBox71 = Val(frmUnitlogo.TextBox71) + C
       
        End If
      End If
      End If
  Next element


'----FLEXFIX-----------------------------------------------------------
For Each element In ThisDrawing.ModelSpace
      If element.ObjectName = "AcDbBlockReference" Then
      If element.Name = "Mat_spe_FLEX" Or element.Name = "Mat_spe_FLEX_Aankoppel" Then
      Set symbool = element
      b = b + 1
        If symbool.HasAttributes Then
        attributen = symbool.GetAttributes
        For j = LBound(attributen) To UBound(attributen)
        Set attribuut = attributen(j)

        If attribuut.TagString = "RNU" Then a = attribuut.textstring
        If a > 10 Then grtwaarde = 1
        If a > 16 Then message = 1
        
        If attribuut.TagString = "FLEX_MATTEN" And attribuut.textstring <> "" Then _
        TextBox55 = TextBox55 + (Val(attribuut.textstring))  'MATTEN
        If attribuut.TagString = "FLEX_METERS" And attribuut.textstring <> "" Then _
        TextBox56 = TextBox56 + (Val(attribuut.textstring))  'METERS
      
        Next j
       
        End If
      End If
      End If
  Next element

'----PE-RT----16*2--14*2-----------------------------------------------------
For Each element In ThisDrawing.ModelSpace
      If element.ObjectName = "AcDbBlockReference" Then
      If element.Name = "Mat_spe_PE" Or element.Name = "Mat_spe_PEringleiding" Or element.Name = "Mat_spe_PE800" Then
      Set symbool = element
      b = b + 1
      If element.Name = "Mat_spe_PE800" Then CheckBox1.Value = True
      If symbool.HasAttributes Then
        attributen = symbool.GetAttributes
        For k = LBound(attributen) To UBound(attributen)
        Set attribuut = attributen(k)
        If attribuut.TagString = "RNU" Then a = attribuut.textstring
        If a > 10 Then grtwaarde = 1
        If a > 16 Then message = 1
        
        
       If attribuut.TagString = "PE" And attribuut.textstring = "PE-RT 16*2 mm" Then
        For l = LBound(attributen) To UBound(attributen)
           Set attribuut = attributen(l)
        If attribuut.TagString = "PE120" And attribuut.textstring <> "" Then TextBox43 = TextBox43 + (Val(attribuut.textstring))  '120 METER
        If attribuut.TagString = "PE90" And attribuut.textstring <> "" Then TextBox44 = TextBox44 + (Val(attribuut.textstring))  '90 METER
        If attribuut.TagString = "PE60" And attribuut.textstring <> "" Then TextBox45 = TextBox45 + (Val(attribuut.textstring))  '60 METER
        Label51 = "PE-RT16"
        Next l
       End If
      
      If attribuut.TagString = "PE" And attribuut.textstring = "PE-RT 14*2 mm" Then
        For m = LBound(attributen) To UBound(attributen)
           Set attribuut = attributen(m)
        If attribuut.TagString = "PE90" And attribuut.textstring <> "" Then TextBox52 = TextBox52 + (Val(attribuut.textstring))  '90 METER
        If attribuut.TagString = "PE60" And attribuut.textstring <> "" Then TextBox53 = TextBox53 + (Val(attribuut.textstring))  '60 METER
        Label52 = "PE-RT14"
        Next m
      End If
        
      If attribuut.TagString = "LMETER" And attribuut.textstring <> "" Then b = attribuut.textstring
          
 
          
       
    Next k
       frmUnitlogo.TextBox70 = Val(frmUnitlogo.TextBox70) + b
   End If
   End If
   End If
  Next element
  
  
  


'----ALUFLEX-----------------------------------------------------------
For Each element In ThisDrawing.ModelSpace
      If element.ObjectName = "AcDbBlockReference" Then
      If element.Name = "Mat_spe_ALU" Or element.Name = "Mat_spe_ALUringleiding" Then
      Set symbool = element
      b = b + 1
      If symbool.HasAttributes Then
        attributen = symbool.GetAttributes
        For t = LBound(attributen) To UBound(attributen)
        Set attribuut = attributen(t)
        If attribuut.TagString = "RNU" Then a = attribuut.textstring
        If a > 10 Then grtwaarde = 1
        If a > 16 Then message = 1
        
        If attribuut.TagString = "ALU200" And attribuut.textstring <> "" Then _
        TextBox47 = TextBox47 + (Val(attribuut.textstring))  '200 METER
        If attribuut.TagString = "ALU100" And attribuut.textstring <> "" Then _
        TextBox48 = TextBox48 + (Val(attribuut.textstring))  '100 METER
        If attribuut.TagString = "ALU50" And attribuut.textstring <> "" Then _
        TextBox49 = TextBox49 + (Val(attribuut.textstring))  '50 METER
        
        
        If attribuut.TagString = "ALU" Then
          Label53 = "ALUFLEX"
          Label29 = attribuut.textstring
        End If
        
        Next t
       
   End If
   End If
   End If
  Next element

'frmUnitlogo.Caption = "Bloklogo's uitlezen  " & L29 & L30 & L31 & L32 'leidingsoort
Label28.Caption = a
Label34.Caption = grtwaarde
If a > 10 Or b > 10 Or grtwaarde = 1 Then
   frmUnitlogo.Height = 385
End If
  
   
'If rol250 = 0 Then rol250 = "-"
'If rol165 = 0 Then rol165 = "-"
'If rol125 = 0 Then rol125 = "-"
'If rol105 = 0 Then rol105 = "-"
'If rol90 = 0 Then rol90 = "-"
'If rol75 = 0 Then rol75 = "-"
'If rol63 = 0 Then rol63 = "-"
'If rol50 = 0 Then rol50 = "-"
'If rol40 = 0 Then rol40 = "-"

'If PE120 = 0 Then PE120 = "-"
'If PE90 = 0 Then PE90 = "-"
'If PE60 = 0 Then PE60 = "-"

'---WTH-ZD----------------------------------------------------
For Each element In ThisDrawing.ModelSpace
        If element.ObjectName = "AcDbBlockReference" Then
            If element.Name = "Mat_spe_ZD" Or element.Name = "Mat_spe_PE" Or element.Name = "Mat_spe_PE800" _
            Or element.Name = "Mat_spe_ALU" Or element.Name = "Mat_spe_ZDringleiding" Or element.Name = "Mat_spe_PEringleiding" _
            Or element.Name = "Mat_spe_ALUringleiding" Or element.Name = "Mat_spe_FLEX" Or element.Name = "Mat_spe_ZD_1627" _
            Or element.Name = "Mat_spe_ZD_1627500" Then
                Set symbool = element
                If symbool.HasAttributes Then
                    attributen = symbool.GetAttributes
                    For I = LBound(attributen) To UBound(attributen)
                         Set attribuut = attributen(I)
                '--------------------------unit 1 t/m 10
                If TextBox1 = "" Then
                  If attribuut.TagString = "RNU" Then t1 = attribuut.textstring
                  If attribuut.TagString = "REGELUNITTYPE" And (t1 = "1" Or t1 = "01") Then TextBox1 = attribuut.textstring
                End If
                If TextBox2 = "" Then
                  If attribuut.TagString = "RNU" Then t2 = attribuut.textstring
                  If attribuut.TagString = "REGELUNITTYPE" And (t2 = "2" Or t2 = "02") Then TextBox2 = attribuut.textstring
                End If
                If TextBox3 = "" Then
                  If attribuut.TagString = "RNU" Then t3 = attribuut.textstring
                  If attribuut.TagString = "REGELUNITTYPE" And (t3 = "3" Or t3 = "03") Then TextBox3 = attribuut.textstring
                End If
                If TextBox4 = "" Then
                  If attribuut.TagString = "RNU" Then t4 = attribuut.textstring
                  If attribuut.TagString = "REGELUNITTYPE" And (t4 = "4" Or t4 = "04") Then TextBox4 = attribuut.textstring
                End If
                If TextBox5 = "" Then
                  If attribuut.TagString = "RNU" Then t5 = attribuut.textstring
                  If attribuut.TagString = "REGELUNITTYPE" And (t5 = "5" Or t5 = "05") Then TextBox5 = attribuut.textstring
                End If
                If TextBox6 = "" Then
                  If attribuut.TagString = "RNU" Then t6 = attribuut.textstring
                  If attribuut.TagString = "REGELUNITTYPE" And (t6 = "6" Or t6 = "06") Then TextBox6 = attribuut.textstring
                End If
                 If TextBox7 = "" Then
                  If attribuut.TagString = "RNU" Then t7 = attribuut.textstring
                  If attribuut.TagString = "REGELUNITTYPE" And (t7 = "7" Or t7 = "07") Then TextBox7 = attribuut.textstring
                End If
                If TextBox8 = "" Then
                  If attribuut.TagString = "RNU" Then t8 = attribuut.textstring
                  If attribuut.TagString = "REGELUNITTYPE" And (t8 = "8" Or t8 = "08") Then TextBox8 = attribuut.textstring
                End If
                'regelunit 9
                If TextBox24 = "" Then
                  If attribuut.TagString = "RNU" Then t9 = attribuut.textstring
                  If attribuut.TagString = "REGELUNITTYPE" And (t9 = "9" Or t9 = "09") Then TextBox24 = attribuut.textstring
                End If
                'regelunit 10
                If TextBox25 = "" Then
                  If attribuut.TagString = "RNU" Then t10 = attribuut.textstring
                  If attribuut.TagString = "REGELUNITTYPE" And t10 = "10" Then TextBox25 = attribuut.textstring
                End If
                
                If TextBox9 = "" Then
                If attribuut.TagString = "BEVESTIGINGSTYPE" And (t1 = "1" Or t1 = "01") Then TextBox9 = attribuut.textstring
                End If
                If TextBox10 = "" Then
                If attribuut.TagString = "BEVESTIGINGSTYPE" And (t2 = "2" Or t2 = "02") Then TextBox10 = attribuut.textstring
                End If
                If TextBox11 = "" Then
                If attribuut.TagString = "BEVESTIGINGSTYPE" And (t3 = "3" Or t3 = "03") Then TextBox11 = attribuut.textstring
                End If
                If TextBox12 = "" Then
                If attribuut.TagString = "BEVESTIGINGSTYPE" And (t4 = "4" Or t4 = "04") Then TextBox12 = attribuut.textstring
                End If
                If TextBox13 = "" Then
                If attribuut.TagString = "BEVESTIGINGSTYPE" And (t5 = "5" Or t5 = "05") Then TextBox13 = attribuut.textstring
                End If
                If TextBox14 = "" Then
                If attribuut.TagString = "BEVESTIGINGSTYPE" And (t6 = "6" Or t6 = "06") Then TextBox14 = attribuut.textstring
                End If
                If TextBox15 = "" Then
                If attribuut.TagString = "BEVESTIGINGSTYPE" And (t7 = "7" Or t7 = "07") Then TextBox15 = attribuut.textstring
                End If
                If TextBox16 = "" Then
                If attribuut.TagString = "BEVESTIGINGSTYPE" And (t8 = "8" Or t8 = "08") Then TextBox16 = attribuut.textstring
                End If
                '--------------------------unit 1 t/m 10
                 
                '--------------------------unit 11 t/m 16
                'If TextBox24 = "" Then
                '  If attribuut.TagString = "RNU" Then t9 = attribuut.TextString
                '  If attribuut.TagString = "REGELUNITTYPE" And (t9 = "9" Or t9 = "09") Then TextBox24 = attribuut.TextString
                'End If
                'If TextBox25 = "" Then
                '  If attribuut.TagString = "RNU" Then t10 = attribuut.TextString
                '  If attribuut.TagString = "REGELUNITTYPE" And t10 = "10" Then TextBox25 = attribuut.TextString
                'End If
                If TextBox26 = "" Then
                  If attribuut.TagString = "RNU" Then t11 = attribuut.textstring
                  If attribuut.TagString = "REGELUNITTYPE" And t11 = "11" Then TextBox26 = attribuut.textstring
                End If
                If TextBox27 = "" Then
                  If attribuut.TagString = "RNU" Then t12 = attribuut.textstring
                  If attribuut.TagString = "REGELUNITTYPE" And t12 = "12" Then TextBox27 = attribuut.textstring
                End If
                If TextBox28 = "" Then
                  If attribuut.TagString = "RNU" Then t13 = attribuut.textstring
                  If attribuut.TagString = "REGELUNITTYPE" And t13 = "13" Then TextBox28 = attribuut.textstring
                End If
                If TextBox29 = "" Then
                  If attribuut.TagString = "RNU" Then t14 = attribuut.textstring
                  If attribuut.TagString = "REGELUNITTYPE" And t14 = "14" Then TextBox29 = attribuut.textstring
                End If
                If TextBox30 = "" Then
                  If attribuut.TagString = "RNU" Then t15 = attribuut.textstring
                  If attribuut.TagString = "REGELUNITTYPE" And t15 = "15" Then TextBox30 = attribuut.textstring
                End If
                If TextBox31 = "" Then
                  If attribuut.TagString = "RNU" Then t16 = attribuut.textstring
                  If attribuut.TagString = "REGELUNITTYPE" And t16 = "16" Then TextBox31 = attribuut.textstring
                End If
                If TextBox32 = "" Then
                If attribuut.TagString = "BEVESTIGINGSTYPE" And (t9 = "9" Or t9 = "09") Then TextBox32 = attribuut.textstring
                End If
                If TextBox33 = "" Then
                If attribuut.TagString = "BEVESTIGINGSTYPE" And t10 = "10" Then TextBox33 = attribuut.textstring
                End If
                If TextBox34 = "" Then
                If attribuut.TagString = "BEVESTIGINGSTYPE" And t11 = "11" Then TextBox34 = attribuut.textstring
                End If
                If TextBox35 = "" Then
                If attribuut.TagString = "BEVESTIGINGSTYPE" And t12 = "12" Then TextBox35 = attribuut.textstring
                End If
                If TextBox36 = "" Then
                If attribuut.TagString = "BEVESTIGINGSTYPE" And t13 = "13" Then TextBox36 = attribuut.textstring
                End If
                If TextBox37 = "" Then
                If attribuut.TagString = "BEVESTIGINGSTYPE" And t14 = "14" Then TextBox37 = attribuut.textstring
                End If
                If TextBox38 = "" Then
                If attribuut.TagString = "BEVESTIGINGSTYPE" And t15 = "15" Then TextBox38 = attribuut.textstring
                End If
                If TextBox39 = "" Then
                If attribuut.TagString = "BEVESTIGINGSTYPE" And t16 = "16" Then TextBox39 = attribuut.textstring
                End If
           
           Next I
              End If
           End If
        End If
    Next element
    
TextBox69 = (Val(TextBox65)) + (Val(TextBox66)) + (Val(TextBox67)) + (Val(TextBox68))
TextBox40 = (Val(TextBox17)) + (Val(TextBox18)) + (Val(TextBox19)) + (Val(TextBox20)) + (Val(TextBox21)) + (Val(TextBox22)) + (Val(TextBox23)) + (Val(TextBox41)) + (Val(TextBox42))
TextBox46 = (Val(TextBox43)) + (Val(TextBox44)) + (Val(TextBox45))
TextBox50 = (Val(TextBox47)) + (Val(TextBox48)) + (Val(TextBox49))
CommandButton1.Enabled = False

If CheckBox1.Value = True Then
   TextBox57 = TextBox43
   TextBox58 = TextBox44
   TextBox59 = TextBox45
   TextBox43 = "0"
   TextBox44 = "0"
   TextBox45 = "0"
   TextBox46 = "0"
   Label64 = 800
End If

If TextBox1 = "" Then TextBox1 = "-"
If TextBox2 = "" Then TextBox2 = "-"
If TextBox3 = "" Then TextBox3 = "-"
If TextBox4 = "" Then TextBox4 = "-"
If TextBox5 = "" Then TextBox5 = "-"
If TextBox6 = "" Then TextBox6 = "-"
If TextBox7 = "" Then TextBox7 = "-"
If TextBox8 = "" Then TextBox8 = "-"
If TextBox9 = "" Then TextBox9 = "-"
If TextBox10 = "" Then TextBox10 = "-"
If TextBox11 = "" Then TextBox11 = "-"
If TextBox12 = "" Then TextBox12 = "-"
If TextBox13 = "" Then TextBox13 = "-"
If TextBox14 = "" Then TextBox14 = "-"
If TextBox15 = "" Then TextBox15 = "-"
If TextBox16 = "" Then TextBox16 = "-"
If TextBox24 = "" Then TextBox24 = "-"
If TextBox25 = "" Then TextBox25 = "-"
If TextBox26 = "" Then TextBox26 = "-"
If TextBox27 = "" Then TextBox27 = "-"
If TextBox28 = "" Then TextBox28 = "-"
If TextBox29 = "" Then TextBox29 = "-"
If TextBox30 = "" Then TextBox30 = "-"
If TextBox31 = "" Then TextBox31 = "-"
If TextBox32 = "" Then TextBox32 = "-"
If TextBox33 = "" Then TextBox33 = "-"
If TextBox34 = "" Then TextBox34 = "-"
If TextBox35 = "" Then TextBox35 = "-"
If TextBox36 = "" Then TextBox36 = "-"
If TextBox37 = "" Then TextBox37 = "-"
If TextBox38 = "" Then TextBox38 = "-"
If TextBox39 = "" Then TextBox39 = "-"
If TextBox41 = "" Then TextBox41 = "-"
If TextBox42 = "" Then TextBox42 = "-"
If TextBox43 = "" Then TextBox43 = "-"
If TextBox44 = "" Then TextBox44 = "-"
If TextBox45 = "" Then TextBox45 = "-"
If TextBox46 = "" Then TextBox46 = "-"
If TextBox47 = "" Then TextBox41 = "-"
If TextBox48 = "" Then TextBox42 = "-"
If TextBox49 = "" Then TextBox43 = "-"
If TextBox50 = "" Then TextBox44 = "-"
If TextBox52 = "" Then TextBox45 = "-"
If TextBox53 = "" Then TextBox46 = "-"
If TextBox54 = "" Then TextBox41 = "-"
If TextBox55 = "" Then TextBox42 = "-"
If TextBox56 = "" Then TextBox43 = "-"
If TextBox57 = "" Then TextBox44 = "-"
If TextBox58 = "" Then TextBox45 = "-"
If TextBox59 = "" Then TextBox46 = "-"
If TextBox60 = "" Then TextBox45 = "-"
If TextBox61 = "" Then TextBox46 = "-"
If TextBox57 = "" Then TextBox44 = "-"


If message = 1 Then MsgBox "Pas op - het aantal units is groter dan 16..!!!!:" & Chr(13) & Chr(10) & Chr(13) & Chr(10) & "1 - Unit 17 en hoger komt NIET in het kaderlogo terecht.!!!" & Chr(13) & "2 - Het aantal groepen klopt wel.", vbExclamation, "Foutmelding"
End Sub
Private Sub TextBox1_Change()
If TextBox1 = "" Then TextBox1 = "-"
End Sub
Private Sub TextBox2_Change()
If TextBox2 = "" Then TextBox2 = "-"
End Sub
Private Sub TextBox3_Change()
If TextBox3 = "" Then TextBox3 = "-"
End Sub
Private Sub TextBox4_Change()
If TextBox4 = "" Then TextBox4 = "-"
End Sub
Private Sub TextBox5_Change()
If TextBox5 = "" Then TextBox5 = "-"
End Sub
Private Sub TextBox6_Change()
If TextBox6 = "" Then TextBox6 = "-"
End Sub
Private Sub TextBox7_Change()
If TextBox7 = "" Then TextBox7 = "-"
End Sub
Private Sub TextBox8_Change()
If TextBox8 = "" Then TextBox8 = "-"
End Sub
Private Sub TextBox9_Change()
If TextBox9 = "" Then TextBox9 = "-"
End Sub
Private Sub TextBox10_Change()
If TextBox10 = "" Then TextBox10 = "-"
End Sub
Private Sub TextBox11_Change()
If TextBox11 = "" Then TextBox11 = "-"
End Sub
Private Sub TextBox12_Change()
If TextBox12 = "" Then TextBox12 = "-"
End Sub
Private Sub TextBox13_Change()
If TextBox13 = "" Then TextBox13 = "-"
End Sub
Private Sub TextBox14_Change()
If TextBox14 = "" Then TextBox14 = "-"
End Sub
Private Sub TextBox15_Change()
If TextBox15 = "" Then TextBox15 = "-"
End Sub
Private Sub TextBox16_Change()
If TextBox16 = "" Then TextBox16 = "-"
End Sub
Private Sub TextBox17_Change()
TextBox40 = (Val(TextBox17)) + (Val(TextBox18)) + (Val(TextBox19)) + (Val(TextBox20)) + (Val(TextBox21)) + (Val(TextBox22)) + (Val(TextBox23)) + (Val(TextBox41)) + (Val(TextBox42))
If TextBox17 = "" Then TextBox17 = "0"
End Sub
Private Sub TextBox18_Change()
TextBox40 = (Val(TextBox17)) + (Val(TextBox18)) + (Val(TextBox19)) + (Val(TextBox20)) + (Val(TextBox21)) + (Val(TextBox22)) + (Val(TextBox23)) + (Val(TextBox41)) + (Val(TextBox42))
If TextBox18 = "" Then TextBox18 = "0"
End Sub
Private Sub TextBox19_Change()
TextBox40 = (Val(TextBox17)) + (Val(TextBox18)) + (Val(TextBox19)) + (Val(TextBox20)) + (Val(TextBox21)) + (Val(TextBox22)) + (Val(TextBox23)) + (Val(TextBox41)) + (Val(TextBox42))
If TextBox19 = "" Then TextBox19 = "0"
End Sub
Private Sub TextBox20_Change()
TextBox40 = (Val(TextBox17)) + (Val(TextBox18)) + (Val(TextBox19)) + (Val(TextBox20)) + (Val(TextBox21)) + (Val(TextBox22)) + (Val(TextBox23)) + (Val(TextBox41)) + (Val(TextBox42))
If TextBox20 = "" Then TextBox20 = "0"
End Sub
Private Sub TextBox21_Change()
TextBox40 = (Val(TextBox17)) + (Val(TextBox18)) + (Val(TextBox19)) + (Val(TextBox20)) + (Val(TextBox21)) + (Val(TextBox22)) + (Val(TextBox23)) + (Val(TextBox41)) + (Val(TextBox42))
If TextBox21 = "" Then TextBox21 = "0"
End Sub
Private Sub TextBox22_Change()
TextBox40 = (Val(TextBox17)) + (Val(TextBox18)) + (Val(TextBox19)) + (Val(TextBox20)) + (Val(TextBox21)) + (Val(TextBox22)) + (Val(TextBox23)) + (Val(TextBox41)) + (Val(TextBox42))
If TextBox22 = "" Then TextBox22 = "0"
End Sub
Private Sub TextBox23_Change()
TextBox40 = (Val(TextBox17)) + (Val(TextBox18)) + (Val(TextBox19)) + (Val(TextBox20)) + (Val(TextBox21)) + (Val(TextBox22)) + (Val(TextBox23)) + (Val(TextBox41)) + (Val(TextBox42))
If TextBox23 = "" Then TextBox23 = "0"
End Sub
Private Sub TextBox41_Change()
TextBox40 = (Val(TextBox17)) + (Val(TextBox18)) + (Val(TextBox19)) + (Val(TextBox20)) + (Val(TextBox21)) + (Val(TextBox22)) + (Val(TextBox23)) + (Val(TextBox41)) + (Val(TextBox42))
If TextBox41 = "" Then TextBox41 = "0"
End Sub
Private Sub TextBox42_Change()
TextBox40 = (Val(TextBox17)) + (Val(TextBox18)) + (Val(TextBox19)) + (Val(TextBox20)) + (Val(TextBox21)) + (Val(TextBox22)) + (Val(TextBox23)) + (Val(TextBox41)) + (Val(TextBox42))
If TextBox42 = "" Then TextBox42 = "0"
End Sub
Private Sub TextBox24_Change()
If TextBox24 = "" Then TextBox24 = "-"
End Sub
Private Sub TextBox25_Change()
If TextBox25 = "" Then TextBox25 = "-"
End Sub
Private Sub TextBox26_Change()
If TextBox26 = "" Then TextBox26 = "-"
End Sub
Private Sub TextBox27_Change()
If TextBox27 = "" Then TextBox27 = "-"
End Sub
Private Sub TextBox28_Change()
If TextBox28 = "" Then TextBox28 = "-"
End Sub
Private Sub TextBox29_Change()
If TextBox29 = "" Then TextBox29 = "-"
End Sub
Private Sub TextBox30_Change()
If TextBox30 = "" Then TextBox30 = "-"
End Sub
Private Sub TextBox31_Change()
If TextBox31 = "" Then TextBox31 = "-"
End Sub
Private Sub TextBox32_Change()
If TextBox32 = "" Then TextBox32 = "-"
End Sub
Private Sub TextBox33_Change()
If TextBox33 = "" Then TextBox33 = "-"
End Sub
Private Sub TextBox34_Change()
If TextBox34 = "" Then TextBox34 = "-"
End Sub
Private Sub TextBox35_Change()
If TextBox35 = "" Then TextBox35 = "-"
End Sub
Private Sub TextBox36_Change()
If TextBox36 = "" Then TextBox36 = "-"
End Sub
Private Sub TextBox37_Change()
If TextBox37 = "" Then TextBox37 = "-"
End Sub
Private Sub TextBox38_Change()
If TextBox38 = "" Then TextBox38 = "-"
End Sub
Private Sub TextBox39_Change()
If TextBox39 = "" Then TextBox39 = "-"
End Sub
Private Sub TextBox43_Change()
TextBox46 = (Val(TextBox43)) + (Val(TextBox44)) + (Val(TextBox45))
If TextBox43 = "" Then TextBox43 = "0"
End Sub
Private Sub TextBox46_Change()
TextBox46 = (Val(TextBox43)) + (Val(TextBox44)) + (Val(TextBox45))
If TextBox46 = "" Then TextBox46 = "0"
End Sub
Private Sub TextBox50_Change()
TextBox50 = (Val(TextBox47)) + (Val(TextBox48)) + (Val(TextBox49))
If TextBox50 = "" Then TextBox50 = "0"
End Sub
Private Sub TextBox52_Change()
TextBox54 = (Val(TextBox52)) + (Val(TextBox53))
If TextBox52 = "" Then TextBox52 = "0"
End Sub
Private Sub TextBox53_Change()
TextBox54 = (Val(TextBox52)) + (Val(TextBox53))
If TextBox53 = "" Then TextBox53 = "0"
End Sub
Private Sub TextBox54_Change()
TextBox54 = (Val(TextBox52)) + (Val(TextBox53))
If TextBox54 = "" Then TextBox54 = "0"
Label52 = "PE-RT14"
End Sub
Private Sub TextBox60_Change()
TextBox60 = (Val(TextBox57)) + (Val(TextBox58)) + (Val(TextBox59)) + (Val(TextBox61))
If TextBox60 = "" Then TextBox60 = "0"
If TextBox60 <> "0" Then
Logoplaats.Enabled = True
cmdschets.Enabled = False
Label64 = 800
End If
End Sub
Private Sub TextBox61_Change()
TextBox60 = (Val(TextBox57)) + (Val(TextBox58)) + (Val(TextBox59)) + (Val(TextBox61))
If TextBox61 = "" Then TextBox61 = "0"
End Sub
Private Sub TextBox57_Change()
TextBox60 = (Val(TextBox57)) + (Val(TextBox58)) + (Val(TextBox59)) + (Val(TextBox61))
If TextBox57 = "" Then TextBox57 = "0"
End Sub
Private Sub TextBox58_Change()
TextBox60 = (Val(TextBox57)) + (Val(TextBox58)) + (Val(TextBox59)) + (Val(TextBox61))
If TextBox58 = "" Then TextBox58 = "0"
End Sub
Private Sub TextBox59_Change()
TextBox60 = (Val(TextBox57)) + (Val(TextBox58)) + (Val(TextBox59)) + (Val(TextBox61))
If TextBox60 = "" Then TextBox60 = "0"
End Sub
Private Sub TextBox65_Change()
TextBox69 = (Val(TextBox65)) + (Val(TextBox66)) + (Val(TextBox67)) + (Val(TextBox68))
If TextBox65 = "" Then TextBox65 = "0"
End Sub
Private Sub TextBox66_Change()
TextBox69 = (Val(TextBox65)) + (Val(TextBox66)) + (Val(TextBox67)) + (Val(TextBox68))
If TextBox66 = "" Then TextBox66 = "0"
End Sub
Private Sub TextBox67_Change()
TextBox69 = (Val(TextBox65)) + (Val(TextBox66)) + (Val(TextBox67)) + (Val(TextBox68))
If TextBox67 = "" Then TextBox67 = "0"
End Sub
Private Sub TextBox68_Change()
TextBox69 = (Val(TextBox65)) + (Val(TextBox66)) + (Val(TextBox67)) + (Val(TextBox68))
If TextBox68 = "" Then TextBox68 = "0"
End Sub
Private Sub Logoplaats_Click()
On Error Resume Next
 'Dim PBEGIN As Variant
 Dim PBEGIN(0 To 2) As Double
 Dim pb2(0 To 2) As Double
 Dim pb3(0 To 2) As Double
 Dim pb4(0 To 2) As Double
 Dim pb5(0 To 2) As Double
 Call Schaal(scaal)
 
frmUnitlogo.Hide
    Set newLayer = ThisDrawing.Layers.Add("UNITLOGO")
    ThisDrawing.ActiveLayer = newLayer
    Update
        
    ThisDrawing.SendCommand "-layer" & vbCr & "U" & vbCr & "*" & vbCr & vbCr
    ThisDrawing.SendCommand "osmode" & vbCr & "1" & vbCr
    Update

    For Each element In ThisDrawing.ModelSpace
      If element.ObjectName = "AcDbBlockReference" Then
         If element.Name = "Kaderlogo" Or element.Name = "ENG-Kaderlogo" Then
          insp = element.InsertionPoint
          PBEGIN(0) = insp(0) - (940 * scaal)
          PBEGIN(1) = insp(1) + (298.7 * scaal)
          PBEGIN(2) = insp(2)
          End If
      Update
      End If
     Next element


'If Not INSP Then pbegin = ThisDrawing.Utility.GetPoint(, "Selecteer beginpunt ")


If TextBox55 <> "0" Then
extraafstand = 30
Dim bestand95 As String
bestand95 = "C:\ACAD2002\DWG\unitlogo_FLEX.dwg"
Set blockRefObj = ThisDrawing.ModelSpace.InsertBlock(PBEGIN, bestand95, scaal, scaal, 1, 0)
Else
extraafstand = 0
End If

If Label28.Caption > 10 Or Label34.Caption = 1 Then  ' meer dan 10 units
 pb2(0) = PBEGIN(0)
 pb2(1) = PBEGIN(1) + (extraafstand * scaal)
 pb2(2) = 0
 Dim bestand96 As String
 bestand96 = "C:\ACAD2002\DWG\unitlogo_extragroepen.dwg"
 Set blockRefObj = ThisDrawing.ModelSpace.InsertBlock(pb2, bestand96, scaal, scaal, 1, 0)
 PBEGIN(0) = pb2(0)
 PBEGIN(1) = pb2(1) + (130.7 * scaal)
 PBEGIN(2) = pb2(2)
 Else
 PBEGIN(0) = PBEGIN(0)
 PBEGIN(1) = PBEGIN(1) + (extraafstand * scaal)
 PBEGIN(2) = PBEGIN(2)
End If


 
'COMBINATIELOGO'S
Dim bestand100 As String
If Label71 = "" And Label50 = "WTH-ZD" And Label51 = "PE-RT16" And Label52 = "" And Label53 = "" And Label64 = "" Then
  bestand100 = "C:\ACAD2002\DWG\unitlogo_ZDPE16.dwg"
  Set blockRefObj = ThisDrawing.ModelSpace.InsertBlock(PBEGIN, bestand100, scaal, scaal, 1, 0)
End If
If Label71 = "" And Label50 = "WTH-ZD" And Label51 = "" And Label52 = "PE-RT14" And Label53 = "" And Label64 = "" Then
bestand100 = "C:\ACAD2002\DWG\unitlogo_ZDPE14.dwg"
  Set blockRefObj = ThisDrawing.ModelSpace.InsertBlock(PBEGIN, bestand100, scaal, scaal, 1, 0)
End If
If Label71 = "" And Label50 = "WTH-ZD" And Label51 = "PE-RT16" And Label52 = "PE-RT14" And Label53 = "" And Label64 = "" Then
bestand100 = "C:\ACAD2002\DWG\unitlogo_ZDPE14-16.dwg"
  Set blockRefObj = ThisDrawing.ModelSpace.InsertBlock(PBEGIN, bestand100, scaal, scaal, 1, 0)
End If
If Label71 = "" And Label50 = "WTH-ZD" And Label51 = "" And Label52 = "" And Label53 = "ALUFLEX" And Label64 = "" Then
bestand100 = "C:\ACAD2002\DWG\unitlogo_ZDALU.dwg"
  Set blockRefObj = ThisDrawing.ModelSpace.InsertBlock(PBEGIN, bestand100, scaal, scaal, 1, 0)
End If
If Label71 = "" And Label50 = "" And Label51 = "" And Label52 = "PE-RT14" And Label53 = "ALUFLEX" And Label64 = "" Then
bestand100 = "C:\ACAD2002\DWG\unitlogo_PE14ALU.dwg"
  Set blockRefObj = ThisDrawing.ModelSpace.InsertBlock(PBEGIN, bestand100, scaal, scaal, 1, 0)
End If

'WTHZD 16*2,7
If Label71 = "WTH-ZD_1627" And Label50 = "WTH-ZD" And Label51 = "" And Label52 = "" And Label53 = "" And Label64 = "" Then
  bestand100 = "C:\ACAD2002\DWG\unitlogo_WTHZD2034_1627.dwg"
  Set blockRefObj = ThisDrawing.ModelSpace.InsertBlock(PBEGIN, bestand100, scaal, scaal, 1, 0)
End If
If Label71 = "WTH-ZD_1627" And Label50 = "" And Label51 = "" And Label52 = "PE-RT14" And Label53 = "" And Label64 = "" Then
  bestand100 = "C:\ACAD2002\DWG\unitlogo_ZD1627PE14.dwg"
  Set blockRefObj = ThisDrawing.ModelSpace.InsertBlock(PBEGIN, bestand100, scaal, scaal, 1, 0)
End If
If Label71 = "WTH-ZD_1627" And Label50 = "" And Label51 = "PE-RT16" And Label52 = "PE-RT14" And Label53 = "" And Label64 = "" Then
bestand100 = "C:\ACAD2002\DWG\unitlogo_ZD1627PE14-16.dwg"
  Set blockRefObj = ThisDrawing.ModelSpace.InsertBlock(PBEGIN, bestand100, scaal, scaal, 1, 0)
End If
If Label71 = "WTH-ZD_1627" And Label50 = "" And Label51 = "" And Label52 = "" And Label53 = "ALUFLEX" And Label64 = "" Then
bestand100 = "C:\ACAD2002\DWG\unitlogo_ZD1627ALU.dwg"
  Set blockRefObj = ThisDrawing.ModelSpace.InsertBlock(PBEGIN, bestand100, scaal, scaal, 1, 0)
End If

If Label71 = "WTH-ZD_1627" And Label50 = "" And Label51 = "PE-RT16" And Label52 = "" And Label53 = "" And Label64 = "800" Then
bestand100 = "C:\ACAD2002\DWG\unitlogo_ZD1627PE16_800.dwg"
  Set blockRefObj = ThisDrawing.ModelSpace.InsertBlock(PBEGIN, bestand100, scaal, scaal, 1, 0)
End If
If Label71 = "WTH-ZD_1627" And Label50 = "" And Label51 = "PE-RT16" And Label52 = "PE-RT14" And Label53 = "" And Label64 = "800" Then
bestand100 = "C:\ACAD2002\DWG\unitlogo_ZD1627PE14-16_800.dwg"
  Set blockRefObj = ThisDrawing.ModelSpace.InsertBlock(PBEGIN, bestand100, scaal, scaal, 1, 0)
End If


    '------ 16 * 2 mm in c.b.n. met ander leiding
If Label71 = "" And Label50 = "" And Label51 = "PE-RT16" And Label52 = "" And Label53 = "ALUFLEX" And Label64 = "" Then
bestand100 = "C:\ACAD2002\DWG\unitlogo_PE16ALU.dwg"
  Set blockRefObj = ThisDrawing.ModelSpace.InsertBlock(PBEGIN, bestand100, scaal, scaal, 1, 0)
End If
If Label71 = "" And Label50 = "" And Label51 = "PE-RT16" And Label52 = "PE-RT14" And Label53 = "" And Label64 = "" Then
bestand100 = "C:\ACAD2002\DWG\unitlogo_PE14PE16.dwg"
  Set blockRefObj = ThisDrawing.ModelSpace.InsertBlock(PBEGIN, bestand100, scaal, scaal, 1, 0)
End If
        '800 meter erbij
If Label71 = "" And Label50 = "" And Label51 = "PE-RT16" And Label52 = "PE-RT14" And Label53 = "" And Label64 = "800" Then
bestand100 = "C:\ACAD2002\DWG\unitlogo_PE14PE16_800.dwg"
  Set blockRefObj = ThisDrawing.ModelSpace.InsertBlock(PBEGIN, bestand100, scaal, scaal, 1, 0)
End If
'----wediplaat
If Label71 = "" And Label50 = "WTH-ZD" And Label51 = "" And Label52 = "" And Label53 = "" And Label64 = "800" And CheckBox3.Value = True Then  '' wthzd i.c.m. wediplaat 29-5-2007
bestand100 = "C:\ACAD2002\DWG\unitlogo_ZDwedi.dwg"
  Set blockRefObj = ThisDrawing.ModelSpace.InsertBlock(PBEGIN, bestand100, scaal, scaal, 1, 0)
End If
If Label71 = "" And Label50 = "" And Label51 = "" And Label52 = "" And Label53 = "" And Label64 = "800" And CheckBox3.Value = True Then  '' wthzd i.c.m. wediplaat 29-5-2007
bestand100 = "C:\ACAD2002\DWG\unitlogo_wedi.dwg"
  Set blockRefObj = ThisDrawing.ModelSpace.InsertBlock(PBEGIN, bestand100, scaal, scaal, 1, 0)
End If
'----wediplaat

If Label71 = "" And Label50 = "WTH-ZD" And Label51 = "PE-RT16" And Label52 = "" And Label53 = "" And Label64 = "800" Then
bestand100 = "C:\ACAD2002\DWG\unitlogo_ZDPE16_800.dwg"
  Set blockRefObj = ThisDrawing.ModelSpace.InsertBlock(PBEGIN, bestand100, scaal, scaal, 1, 0)
End If
If Label71 = "" And Label50 = "WTH-ZD" And Label51 = "PE-RT16" And Label52 = "PE-RT14" And Label53 = "" And Label64 = "800" Then
bestand100 = "C:\ACAD2002\DWG\unitlogo_ZDPE14-16_800.dwg"
  Set blockRefObj = ThisDrawing.ModelSpace.InsertBlock(PBEGIN, bestand100, scaal, scaal, 1, 0)
End If
If Label71 = "" And Label50 = "" And Label51 = "PE-RT16" And Label52 = "" And Label53 = "ALUFLEX" And Label64 = "800" Then
bestand100 = "C:\ACAD2002\DWG\unitlogo_PE16ALU_800.dwg"
  Set blockRefObj = ThisDrawing.ModelSpace.InsertBlock(PBEGIN, bestand100, scaal, scaal, 1, 0)
End If

'ENKELE LOGO'S ----------------------------------------------------------------------------------------------------------------

If Label71 = "" And Label50 = "" And Label51 = "" And Label52 = "" And Label53 = "" And Label64 = "" And TextBox55 <> "0" Then
bestand100 = "C:\ACAD2002\DWG\unitlogo_FLEXFIX.dwg"
  Set blockRefObj = ThisDrawing.ModelSpace.InsertBlock(PBEGIN, bestand100, scaal, scaal, 1, 0)
End If
If Label71 = "" And Label50 = "WTH-ZD" And Label51 = "" And Label52 = "" And Label53 = "" And Label64 = "" Then
bestand100 = "C:\ACAD2002\DWG\unitlogo_WTHZD.dwg"
  Set blockRefObj = ThisDrawing.ModelSpace.InsertBlock(PBEGIN, bestand100, scaal, scaal, 1, 0)
End If
If Label71 = "WTH-ZD_1627" And Label50 = "" And Label51 = "" And Label52 = "" And Label53 = "" And Label64 = "" Then
bestand100 = "C:\ACAD2002\DWG\unitlogo_WTHZD1627.dwg"
  Set blockRefObj = ThisDrawing.ModelSpace.InsertBlock(PBEGIN, bestand100, scaal, scaal, 1, 0)
End If
If Label71 = "" And Label51 = "PE-RT16" And Label50 = "" And Label52 = "" And Label53 = "" And Label64 = "" Then
bestand100 = "C:\ACAD2002\DWG\unitlogo_PERT16.dwg"
  Set blockRefObj = ThisDrawing.ModelSpace.InsertBlock(PBEGIN, bestand100, scaal, scaal, 1, 0)
End If
If Label71 = "" And Label51 = "" And Label50 = "" And Label52 = "" And Label53 = "" And Label64 = "" And CheckBox5.Value = True Then
bestand100 = "C:\ACAD2002\DWG\unitlogo_WTHZD1627werkleng.dwg"
  Set blockRefObj = ThisDrawing.ModelSpace.InsertBlock(PBEGIN, bestand100, scaal, scaal, 1, 0)
End If


'------------------------800 meter----hier
If Label71 = "" And Label51 = "PE-RT16" And Label50 = "" And Label52 = "" And Label53 = "" And Label64 = "800" And CheckBox4 = False Then
  bestand100 = "C:\ACAD2002\DWG\unitlogo_PERT16_800.dwg"
  Set blockRefObj = ThisDrawing.ModelSpace.InsertBlock(PBEGIN, bestand100, scaal, scaal, 1, 0)
End If
If Label71 = "" And Label51 = "PE-RT16" And Label50 = "" And Label52 = "" And Label53 = "" And Label64 = "800" And CheckBox4 = True Then
  bestand100 = "C:\ACAD2002\DWG\unitlogo_PERT16_800wk.dwg"
  Set blockRefObj = ThisDrawing.ModelSpace.InsertBlock(PBEGIN, bestand100, scaal, scaal, 1, 0)
End If
'------------------------800 meter




If Label71 = "" And Label52 = "PE-RT14" And Label50 = "" And Label51 = "" And Label53 = "" And Label64 = "" Then
bestand100 = "C:\ACAD2002\DWG\unitlogo_PERT14.dwg"
  Set blockRefObj = ThisDrawing.ModelSpace.InsertBlock(PBEGIN, bestand100, scaal, scaal, 1, 0)
End If
If Label71 = "" And Label53 = "ALUFLEX" And Label50 = "" And Label51 = "" And Label52 = "" And Label64 = "" Then
bestand100 = "C:\ACAD2002\DWG\unitlogo_ALU.dwg"
  Set blockRefObj = ThisDrawing.ModelSpace.InsertBlock(PBEGIN, bestand100, scaal, scaal, 1, 0)
End If

'If TextBox55 <> "0" And (TextBox40 = "0" And TextBox46 = "0" And TextBox50 = "0" And TextBox54 = "0") Then
'xp = 0
'Else
xp = 254.5 * scaal
'End If

 pb3(0) = PBEGIN(0)
 pb3(1) = PBEGIN(1) + xp '(254.5 * scaal)
 pb3(2) = 0

Dim bestand101 As String
bestand101 = "C:\ACAD2002\DWG\bl-krimp.dwg"
Set blockRefObj = ThisDrawing.ModelSpace.InsertBlock(pb3, bestand101, scaal, scaal, 1, 0)

 pb4(0) = pb3(0)
 pb4(1) = pb3(1) + (77 * scaal)
 pb4(2) = 0
 
 
Dim bestand102 As String
bestand102 = "C:\ACAD2002\DWG\bl-recht.dwg"
Set blockRefObj = ThisDrawing.ModelSpace.InsertBlock(pb4, bestand102, scaal, scaal, 1, 0)

 pb5(0) = pb4(0)
 pb5(1) = pb4(1) + (77 * scaal)
 pb5(2) = 0


Dim bestand103 As String
bestand103 = "C:\ACAD2002\DWG\bl-hr.dwg"
Set blockRefObj = ThisDrawing.ModelSpace.InsertBlock(pb5, bestand103, scaal, scaal, 1, 0)


If Err Then
    frmUnitlogo.Show
    Exit Sub
    End If

Call vulunitlogoin
Update
 ThisDrawing.SendCommand "osmode" & vbCr & "0" & vbCr
Unload Me

End Sub
Sub vulunitlogoin()
'bloklogo invullen WTH-ZD
        If TextBox17 = "0" Then TextBox17 = "-"
        If TextBox18 = "0" Then TextBox18 = "-"
        If TextBox19 = "0" Then TextBox19 = "-"
        If TextBox20 = "0" Then TextBox20 = "-"
        If TextBox21 = "0" Then TextBox21 = "-"
        If TextBox22 = "0" Then TextBox22 = "-"
        If TextBox23 = "0" Then TextBox23 = "-"
        If TextBox41 = "0" Then TextBox41 = "-"
        If TextBox42 = "0" Then TextBox42 = "-"
        
        If TextBox43 = "0" Then TextBox43 = "-"
        If TextBox44 = "0" Then TextBox44 = "-"
        If TextBox45 = "0" Then TextBox45 = "-"
        
        If TextBox47 = "0" Then TextBox47 = "-"
        If TextBox48 = "0" Then TextBox48 = "-"
        If TextBox49 = "0" Then TextBox49 = "-"
        
        If TextBox52 = "0" Then TextBox52 = "-"
        If TextBox53 = "0" Then TextBox53 = "-"
        
        If TextBox57 = "0" Then TextBox57 = "-"
        If TextBox58 = "0" Then TextBox58 = "-"
        If TextBox59 = "0" Then TextBox59 = "-"
        If TextBox61 = "0" Then TextBox61 = "-"

        If TextBox65 = "0" Then TextBox65 = "-"
        If TextBox66 = "0" Then TextBox66 = "-"
        If TextBox67 = "0" Then TextBox67 = "-"
        If TextBox68 = "0" Then TextBox68 = "-"
        
        

For Each element In ThisDrawing.ModelSpace
      If element.ObjectName = "AcDbBlockReference" Then
      If element.Name = "unitlogo_WTHZD" Or element.Name = "unitlogo_ZDPE16" Or element.Name = "unitlogo_ZDPE16_800" _
        Or element.Name = "unitlogo_ZDPE14" Or element.Name = "unitlogo_ZDPE14-16" Or element.Name = "unitlogo_ZDPE14-16_800" _
        Or element.Name = "unitlogo_ZDALU" Or element.Name = "unitlogo_FLEXFIX" Or element.Name = "unitlogo_ZDwedi" _
        Or element.Name = "unitlogo_wedi" _
        Or element.Name = "unitlogo_WTHZD1627" Or element.Name = "unitlogo_WTHZD2034_1627" Or element.Name = "unitlogo_ZD1627PE16" _
        Or element.Name = "unitlogo_ZD1627PE16_800" Or element.Name = "unitlogo_ZD1627ALU" Or element.Name = "unitlogo_ZD1627PE14-16" _
        Or element.Name = "unitlogo_ZD1627PE14-16_800" Or element.Name = "unitlogo_ZD1627PE14" Or element.Name = "unitlogo_WTHZD1627werkleng" Then
   
      Set symbool = element
        If symbool.HasAttributes Then
        attributen = symbool.GetAttributes
        For j = LBound(attributen) To UBound(attributen)
        Set attribuut = attributen(j)
        If attribuut.TagString = "U_REGELUNITTYPE1" And attribuut.textstring = "" Then attribuut.textstring = TextBox1 'REGELUNIT1
        If attribuut.TagString = "U_REGELUNITTYPE2" And attribuut.textstring = "" Then attribuut.textstring = TextBox2 'REGELUNIT2
        If attribuut.TagString = "U_REGELUNITTYPE3" And attribuut.textstring = "" Then attribuut.textstring = TextBox3 'REGELUNIT3
        If attribuut.TagString = "U_REGELUNITTYPE4" And attribuut.textstring = "" Then attribuut.textstring = TextBox4 'REGELUNIT4
        If attribuut.TagString = "U_REGELUNITTYPE5" And attribuut.textstring = "" Then attribuut.textstring = TextBox5 'REGELUNIT5
        If attribuut.TagString = "U_REGELUNITTYPE6" And attribuut.textstring = "" Then attribuut.textstring = TextBox6 'REGELUNIT6
        If attribuut.TagString = "U_REGELUNITTYPE7" And attribuut.textstring = "" Then attribuut.textstring = TextBox7 'REGELUNIT7
        If attribuut.TagString = "U_REGELUNITTYPE8" And attribuut.textstring = "" Then attribuut.textstring = TextBox8 'REGELUNIT8
        If attribuut.TagString = "U_REGELUNITTYPE9" And attribuut.textstring = "" Then attribuut.textstring = TextBox24 'REGELUNIT9
        If attribuut.TagString = "U_REGELUNITTYPE10" And attribuut.textstring = "" Then attribuut.textstring = TextBox25 'REGELUNIT10
       
        If attribuut.TagString = "U_BEVESTIGINGSTYPE1" And attribuut.textstring = "" Then attribuut.textstring = TextBox9 'BEVESTIGING1
        If attribuut.TagString = "U_BEVESTIGINGSTYPE2" And attribuut.textstring = "" Then attribuut.textstring = TextBox10 'BEVESTIGING2
        If attribuut.TagString = "U_BEVESTIGINGSTYPE3" And attribuut.textstring = "" Then attribuut.textstring = TextBox11 'BEVESTIGING3
        If attribuut.TagString = "U_BEVESTIGINGSTYPE4" And attribuut.textstring = "" Then attribuut.textstring = TextBox12 'BEVESTIGING4
        If attribuut.TagString = "U_BEVESTIGINGSTYPE5" And attribuut.textstring = "" Then attribuut.textstring = TextBox13 'BEVESTIGING5
        If attribuut.TagString = "U_BEVESTIGINGSTYPE6" And attribuut.textstring = "" Then attribuut.textstring = TextBox14 'BEVESTIGING6
        If attribuut.TagString = "U_BEVESTIGINGSTYPE7" And attribuut.textstring = "" Then attribuut.textstring = TextBox15 'BEVESTIGING7
        If attribuut.TagString = "U_BEVESTIGINGSTYPE8" And attribuut.textstring = "" Then attribuut.textstring = TextBox16 'BEVESTIGING8
        If attribuut.TagString = "U_BEVESTIGINGSTYPE9" And attribuut.textstring = "" Then attribuut.textstring = TextBox32 'BEVESTIGING9
        If attribuut.TagString = "U_BEVESTIGINGSTYPE10" And attribuut.textstring = "" Then attribuut.textstring = TextBox33 'BEVESTIGING10
        

        If attribuut.TagString = "U_WTH250" And attribuut.textstring = "" Then attribuut.textstring = TextBox17 '250 METER
        If attribuut.TagString = "U_WTH165" And attribuut.textstring = "" Then attribuut.textstring = TextBox18 '165 METER
        If attribuut.TagString = "U_WTH125" And attribuut.textstring = "" Then attribuut.textstring = TextBox19 '125 METER
        If attribuut.TagString = "U_WTH105" And attribuut.textstring = "" Then attribuut.textstring = TextBox20 '105 METER
        If attribuut.TagString = "U_WTH90" And attribuut.textstring = "" Then attribuut.textstring = TextBox21 '90 METER
        If attribuut.TagString = "U_WTH75" And attribuut.textstring = "" Then attribuut.textstring = TextBox22 '75 METER
        If attribuut.TagString = "U_WTH63" And attribuut.textstring = "" Then attribuut.textstring = TextBox23 '63 METER
        If attribuut.TagString = "U_WTH50" And attribuut.textstring = "" Then attribuut.textstring = TextBox41 '50 METER
        If attribuut.TagString = "U_WTH40" And attribuut.textstring = "" Then attribuut.textstring = TextBox42 '40 METER
        If attribuut.TagString = "U_WTH120" And attribuut.textstring = "" Then attribuut.textstring = TextBox17 '120 METER
        If attribuut.TagString = "U_WTH90" And attribuut.textstring = "" Then attribuut.textstring = TextBox18 '90 METER
        If attribuut.TagString = "U_WTH60" And attribuut.textstring = "" Then attribuut.textstring = TextBox19 '60 METER
        If attribuut.TagString = "U_TOTAAL" And attribuut.textstring = "" Then attribuut.textstring = TextBox40 'TOTAAL AANTAL GROEPEN
        If attribuut.TagString = "U_TOTAALPE16" And attribuut.textstring = "" Then attribuut.textstring = TextBox70 'TOTAAL AANTAL GROEPEN
        
        'WTHZD "16*2,7
        If element.Name = "unitlogo_WTHZD1627" Or element.Name = "unitlogo_ZD1627PE14" _
           Or element.Name = "unitlogo_ZD1627PE14-16" Or element.Name = "unitlogo_ZD1627ALU" _
           Or element.Name = "unitlogo_ZD1627PE16_800" Or element.Name = "unitlogo_WTHZD1627werkleng" Then
            Set symbool = element
            If symbool.HasAttributes Then
            attributen = symbool.GetAttributes
            For P = LBound(attributen) To UBound(attributen)
            Set attribuut = attributen(P)
            
             If attribuut.TagString = "U_WTH105" And attribuut.textstring = "" Then attribuut.textstring = TextBox65 '105 METER
             If attribuut.TagString = "U_WTH90" And attribuut.textstring = "" Then attribuut.textstring = TextBox66 '90 METER
             If attribuut.TagString = "U_WTH75" And attribuut.textstring = "" Then attribuut.textstring = TextBox67 '75 METER
             If attribuut.TagString = "U_WTH63" And attribuut.textstring = "" Then attribuut.textstring = TextBox68 '63 METER
             If attribuut.TagString = "U_TOTAAL" And attribuut.textstring = "" Then attribuut.textstring = TextBox69 'TOTAAL AANTAL GROEPEN
             If attribuut.TagString = "U_TOTAALWERKLENG" And attribuut.textstring = "" Then attribuut.textstring = TextBox71 'TOTAAL AANTAL GROEPEN 500 meter
             'PE14
              If attribuut.TagString = "U_WTH1490" And attribuut.textstring = "" Then attribuut.textstring = TextBox52 '90 METER
              If attribuut.TagString = "U_WTH1460" And attribuut.textstring = "" Then attribuut.textstring = TextBox53 '60 METER
              If attribuut.TagString = "U_TOTAALPE14" And attribuut.textstring = "" Then attribuut.textstring = TextBox54 'TOTAAL PERT
             'PE16
             If attribuut.TagString = "U_WTH16120" And attribuut.textstring = "" Then attribuut.textstring = TextBox43 '120 METER
             If attribuut.TagString = "U_WTH1690" And attribuut.textstring = "" Then attribuut.textstring = TextBox44 '90 METER
             If attribuut.TagString = "U_WTH1660" And attribuut.textstring = "" Then attribuut.textstring = TextBox45 '60 METER
             If attribuut.TagString = "U_TOTAALPE16" And attribuut.textstring = "" Then attribuut.textstring = TextBox46 'TOTAAL PERT
             'ALUFLEX
              If attribuut.TagString = "ALU200" And attribuut.textstring = "" Then attribuut.textstring = TextBox47 '200 METER
              If attribuut.TagString = "ALU100" And attribuut.textstring = "" Then attribuut.textstring = TextBox48 '100 METER
              If attribuut.TagString = "ALU50" And attribuut.textstring = "" Then attribuut.textstring = TextBox49 '50 METER
              If attribuut.TagString = "ALUFLEX" Then attribuut.textstring = Label29  '60 METER
              If attribuut.TagString = "ALU_TOTAAL" And attribuut.textstring = "" Then attribuut.textstring = TextBox50 'TOTAAL AANTAL GROEPEN
             '800 METER
              If attribuut.TagString = "U_WTH16800" And attribuut.textstring = "" Then attribuut.textstring = TextBox61 '800 METER
              If attribuut.TagString = "U_WTH16120_800" And attribuut.textstring = "" Then attribuut.textstring = TextBox57 '120 METER
              If attribuut.TagString = "U_WTH1690_800" And attribuut.textstring = "" Then attribuut.textstring = TextBox58 '90 METER
              If attribuut.TagString = "U_WTH1660_800" And attribuut.textstring = "" Then attribuut.textstring = TextBox59 '60 METER
              If attribuut.TagString = "U_TOTAALPE16800" And attribuut.textstring = "" Then attribuut.textstring = TextBox60 'TOTAAL PERT
             Next P
             End If
        End If
         'WTHZD "16*2,7 + WTH-ZD 20*3,4
        If element.Name = "unitlogo_WTHZD2034_1627" Then
            Set symbool = element
            If symbool.HasAttributes Then
            attributen = symbool.GetAttributes
            For PE = LBound(attributen) To UBound(attributen)
            Set attribuut = attributen(PE)
            
             If attribuut.TagString = "U_WTH105_1627" And attribuut.textstring = "" Then attribuut.textstring = TextBox65 '105 METER
             If attribuut.TagString = "U_WTH90_1627" And attribuut.textstring = "" Then attribuut.textstring = TextBox66 '90 METER
             If attribuut.TagString = "U_WTH75_1627" And attribuut.textstring = "" Then attribuut.textstring = TextBox67 '75 METER
             If attribuut.TagString = "U_WTH63_1627" And attribuut.textstring = "" Then attribuut.textstring = TextBox68 '63 METER
             If attribuut.TagString = "U_TOTAAL_1627" And attribuut.textstring = "" Then attribuut.textstring = TextBox69 'TOTAAL AANTAL GROEPEN
             Next PE
             End If
        End If
        
        If CheckBox1.Value = False Then
        '--PERT 16*2
        If attribuut.TagString = "U_WTH16120" And attribuut.textstring = "" Then attribuut.textstring = TextBox43 '120 METER
        If attribuut.TagString = "U_WTH1690" And attribuut.textstring = "" Then attribuut.textstring = TextBox44 '90 METER
        If attribuut.TagString = "U_WTH1660" And attribuut.textstring = "" Then attribuut.textstring = TextBox45 '60 METER
        If attribuut.TagString = "U_TOTAALPE16" And attribuut.textstring = "" Then attribuut.textstring = TextBox46 'TOTAAL PERT
        Else '---+ 800 meter
        If attribuut.TagString = "U_WTH16800" And attribuut.textstring = "" Then attribuut.textstring = TextBox61 '800 METER
        If attribuut.TagString = "U_WTH16120" And attribuut.textstring = "" Then attribuut.textstring = TextBox57 '120 METER
        If attribuut.TagString = "U_WTH1690" And attribuut.textstring = "" Then attribuut.textstring = TextBox58 '90 METER
        If attribuut.TagString = "U_WTH1660" And attribuut.textstring = "" Then attribuut.textstring = TextBox59 '60 METER
        If attribuut.TagString = "U_TOTAALPE16" And attribuut.textstring = "" Then attribuut.textstring = TextBox60 'TOTAAL PERT
        End If
        
        
        '--PERT 14*2
        If attribuut.TagString = "U_WTH1490" And attribuut.textstring = "" Then attribuut.textstring = TextBox52 '90 METER
        If attribuut.TagString = "U_WTH1460" And attribuut.textstring = "" Then attribuut.textstring = TextBox53 '60 METER
        If attribuut.TagString = "U_TOTAALPE14" And attribuut.textstring = "" Then attribuut.textstring = TextBox54 'TOTAAL PERT
         
         'End If
         
         
         
         
       Next j
       
       End If
      End If
     End If
  Next element
 'End If
 
 For Each element In ThisDrawing.ModelSpace
      If element.ObjectName = "AcDbBlockReference" Then
      If element.Name = "unitlogo_PERT14" Or element.Name = "unitlogo_PERT16" Or element.Name = "unitlogo_PERT16_800" _
      Or element.Name = "unitlogo_PE14PE16" Or element.Name = "unitlogo_PERT16_800wk" Or element.Name = "unitlogo_PE14PE16_800" Then
      Set symbool = element
        If symbool.HasAttributes Then
        attributen = symbool.GetAttributes
        For m = LBound(attributen) To UBound(attributen)
        Set attribuut = attributen(m)
        If attribuut.TagString = "U_REGELUNITTYPE1" And attribuut.textstring = "" Then attribuut.textstring = TextBox1 'REGELUNIT1
        If attribuut.TagString = "U_REGELUNITTYPE2" And attribuut.textstring = "" Then attribuut.textstring = TextBox2 'REGELUNIT2
        If attribuut.TagString = "U_REGELUNITTYPE3" And attribuut.textstring = "" Then attribuut.textstring = TextBox3 'REGELUNIT3
        If attribuut.TagString = "U_REGELUNITTYPE4" And attribuut.textstring = "" Then attribuut.textstring = TextBox4 'REGELUNIT4
        If attribuut.TagString = "U_REGELUNITTYPE5" And attribuut.textstring = "" Then attribuut.textstring = TextBox5 'REGELUNIT5
        If attribuut.TagString = "U_REGELUNITTYPE6" And attribuut.textstring = "" Then attribuut.textstring = TextBox6 'REGELUNIT6
        If attribuut.TagString = "U_REGELUNITTYPE7" And attribuut.textstring = "" Then attribuut.textstring = TextBox7 'REGELUNIT7
        If attribuut.TagString = "U_REGELUNITTYPE8" And attribuut.textstring = "" Then attribuut.textstring = TextBox8 'REGELUNIT8
        If attribuut.TagString = "U_REGELUNITTYPE9" And attribuut.textstring = "" Then attribuut.textstring = TextBox24 'REGELUNIT9
        If attribuut.TagString = "U_REGELUNITTYPE10" And attribuut.textstring = "" Then attribuut.textstring = TextBox25 'REGELUNIT10

        If attribuut.TagString = "U_BEVESTIGINGSTYPE1" And attribuut.textstring = "" Then attribuut.textstring = TextBox9 'BEVESTIGING1
        If attribuut.TagString = "U_BEVESTIGINGSTYPE2" And attribuut.textstring = "" Then attribuut.textstring = TextBox10 'BEVESTIGING2
        If attribuut.TagString = "U_BEVESTIGINGSTYPE3" And attribuut.textstring = "" Then attribuut.textstring = TextBox11 'BEVESTIGING3
        If attribuut.TagString = "U_BEVESTIGINGSTYPE4" And attribuut.textstring = "" Then attribuut.textstring = TextBox12 'BEVESTIGING4
        If attribuut.TagString = "U_BEVESTIGINGSTYPE5" And attribuut.textstring = "" Then attribuut.textstring = TextBox13 'BEVESTIGING5
        If attribuut.TagString = "U_BEVESTIGINGSTYPE6" And attribuut.textstring = "" Then attribuut.textstring = TextBox14 'BEVESTIGING6
        If attribuut.TagString = "U_BEVESTIGINGSTYPE7" And attribuut.textstring = "" Then attribuut.textstring = TextBox15 'BEVESTIGING7
        If attribuut.TagString = "U_BEVESTIGINGSTYPE8" And attribuut.textstring = "" Then attribuut.textstring = TextBox16 'BEVESTIGING8
        If attribuut.TagString = "U_BEVESTIGINGSTYPE9" And attribuut.textstring = "" Then attribuut.textstring = TextBox32 'BEVESTIGING9
        If attribuut.TagString = "U_BEVESTIGINGSTYPE10" And attribuut.textstring = "" Then attribuut.textstring = TextBox33 'BEVESTIGING10
        
        If CheckBox1.Value = False Then
        '--PERT 16*2
        If attribuut.TagString = "U_WTH16120" And attribuut.textstring = "" Then attribuut.textstring = TextBox43 '120 METER
        If attribuut.TagString = "U_WTH1690" And attribuut.textstring = "" Then attribuut.textstring = TextBox44 '90 METER
        If attribuut.TagString = "U_WTH1660" And attribuut.textstring = "" Then attribuut.textstring = TextBox45 '60 METER
        If attribuut.TagString = "U_TOTAALPE16" And attribuut.textstring = "" Then attribuut.textstring = TextBox46 'TOTAAL PERT
        Else '---+ 800 meter
        If attribuut.TagString = "U_WTH16800" And attribuut.textstring = "" Then attribuut.textstring = TextBox61 '800 METER
        If attribuut.TagString = "U_WTH16120" And attribuut.textstring = "" Then attribuut.textstring = TextBox57 '120 METER
        If attribuut.TagString = "U_WTH1690" And attribuut.textstring = "" Then attribuut.textstring = TextBox58 '90 METER
        If attribuut.TagString = "U_WTH1660" And attribuut.textstring = "" Then attribuut.textstring = TextBox59 '60 METER
        If attribuut.TagString = "U_TOTAALPE16" And attribuut.textstring = "" And element.Name = "unitlogo_PERT16_800" Then
            attribuut.textstring = TextBox60 'TOTAAL PERT
        End If
        If attribuut.TagString = "U_TOTAALPE16" And attribuut.textstring = "" And element.Name = "unitlogo_PERT16_800wk" Then
            attribuut.textstring = TextBox70 'TOTAAL PERT
        End If
        
        End If
        
        
''        '--PE 16
''        If attribuut.TagString = "U_WTH16120" And attribuut.TextString = "" Then attribuut.TextString = TextBox43 '120 METER
''        If attribuut.TagString = "U_WTH1690" And attribuut.TextString = "" Then attribuut.TextString = TextBox44 '90 METER
''        If attribuut.TagString = "U_WTH1660" And attribuut.TextString = "" Then attribuut.TextString = TextBox45 '60 METER
''       ' If attribuut.TagString = "PERT" And attribuut.TextString = "" And Label51 = "PE-RT16" Then attribuut.TextString = "PE-RT 16*2 mm"
''        If attribuut.TagString = "U_TOTAALPE16" And attribuut.TextString = "" Then attribuut.TextString = TextBox46 'TOTAAL AANTAL GROEPEN
        
        '--PE 14
        If attribuut.TagString = "U_WTH1490" And attribuut.textstring = "" Then attribuut.textstring = TextBox52 '90 METER
        If attribuut.TagString = "U_WTH1460" And attribuut.textstring = "" Then attribuut.textstring = TextBox53 '60 METER
       ' If attribuut.TagString = "PERT" And attribuut.TextString = "" And Label52 = "PE-RT14" Then attribuut.TextString = "PE-RT 14*2 mm"
        If attribuut.TagString = "U_TOTAALPE14" And attribuut.textstring = "" Then attribuut.textstring = TextBox54 'TOTAAL AANTAL GROEPEN
        
        'End If
                
       
       Next m
       
       End If
      End If
     End If
  Next element
 
 For Each element In ThisDrawing.ModelSpace
      If element.ObjectName = "AcDbBlockReference" Then
      If element.Name = "unitlogo_ZDALU" Or element.Name = "unitlogo_PE14ALU" Or element.Name = "unitlogo_PE16ALU" _
      Or element.Name = "unitlogo_PE16ALU_800" Or element.Name = "unitlogo_ALU" Then
      Set symbool = element
        If symbool.HasAttributes Then
        attributen = symbool.GetAttributes
        For m = LBound(attributen) To UBound(attributen)
        Set attribuut = attributen(m)
        If attribuut.TagString = "U_REGELUNITTYPE1" And attribuut.textstring = "" Then attribuut.textstring = TextBox1 'REGELUNIT1
        If attribuut.TagString = "U_REGELUNITTYPE2" And attribuut.textstring = "" Then attribuut.textstring = TextBox2 'REGELUNIT2
        If attribuut.TagString = "U_REGELUNITTYPE3" And attribuut.textstring = "" Then attribuut.textstring = TextBox3 'REGELUNIT3
        If attribuut.TagString = "U_REGELUNITTYPE4" And attribuut.textstring = "" Then attribuut.textstring = TextBox4 'REGELUNIT4
        If attribuut.TagString = "U_REGELUNITTYPE5" And attribuut.textstring = "" Then attribuut.textstring = TextBox5 'REGELUNIT5
        If attribuut.TagString = "U_REGELUNITTYPE6" And attribuut.textstring = "" Then attribuut.textstring = TextBox6 'REGELUNIT6
        If attribuut.TagString = "U_REGELUNITTYPE7" And attribuut.textstring = "" Then attribuut.textstring = TextBox7 'REGELUNIT7
        If attribuut.TagString = "U_REGELUNITTYPE8" And attribuut.textstring = "" Then attribuut.textstring = TextBox8 'REGELUNIT8
        If attribuut.TagString = "U_REGELUNITTYPE9" And attribuut.textstring = "" Then attribuut.textstring = TextBox24 'REGELUNIT9
        If attribuut.TagString = "U_REGELUNITTYPE10" And attribuut.textstring = "" Then attribuut.textstring = TextBox25 'REGELUNIT10
 
        If attribuut.TagString = "U_BEVESTIGINGSTYPE1" And attribuut.textstring = "" Then attribuut.textstring = TextBox9 'BEVESTIGING1
        If attribuut.TagString = "U_BEVESTIGINGSTYPE2" And attribuut.textstring = "" Then attribuut.textstring = TextBox10 'BEVESTIGING2
        If attribuut.TagString = "U_BEVESTIGINGSTYPE3" And attribuut.textstring = "" Then attribuut.textstring = TextBox11 'BEVESTIGING3
        If attribuut.TagString = "U_BEVESTIGINGSTYPE4" And attribuut.textstring = "" Then attribuut.textstring = TextBox12 'BEVESTIGING4
        If attribuut.TagString = "U_BEVESTIGINGSTYPE5" And attribuut.textstring = "" Then attribuut.textstring = TextBox13 'BEVESTIGING5
        If attribuut.TagString = "U_BEVESTIGINGSTYPE6" And attribuut.textstring = "" Then attribuut.textstring = TextBox14 'BEVESTIGING6
        If attribuut.TagString = "U_BEVESTIGINGSTYPE7" And attribuut.textstring = "" Then attribuut.textstring = TextBox15 'BEVESTIGING7
        If attribuut.TagString = "U_BEVESTIGINGSTYPE8" And attribuut.textstring = "" Then attribuut.textstring = TextBox16 'BEVESTIGING8
        If attribuut.TagString = "U_BEVESTIGINGSTYPE9" And attribuut.textstring = "" Then attribuut.textstring = TextBox32 'BEVESTIGING9
        If attribuut.TagString = "U_BEVESTIGINGSTYPE10" And attribuut.textstring = "" Then attribuut.textstring = TextBox33 'BEVESTIGING10
        If attribuut.TagString = "ALU200" And attribuut.textstring = "" Then attribuut.textstring = TextBox47 '200 METER
        If attribuut.TagString = "ALU100" And attribuut.textstring = "" Then attribuut.textstring = TextBox48 '100 METER
        If attribuut.TagString = "ALU50" And attribuut.textstring = "" Then attribuut.textstring = TextBox49 '50 METER
        If attribuut.TagString = "ALUFLEX" Then attribuut.textstring = Label29  '60 METER
        If attribuut.TagString = "ALU_TOTAAL" And attribuut.textstring = "" Then attribuut.textstring = TextBox50 'TOTAAL AANTAL GROEPEN
        'End If
''           '--PE 16
''        If attribuut.TagString = "U_WTH16120" And attribuut.TextString = "" Then attribuut.TextString = TextBox43 '120 METER
''        If attribuut.TagString = "U_WTH1690" And attribuut.TextString = "" Then attribuut.TextString = TextBox44 '90 METER
''        If attribuut.TagString = "U_WTH1660" And attribuut.TextString = "" Then attribuut.TextString = TextBox45 '60 METER
''       ' If attribuut.TagString = "PERT" And attribuut.TextString = "" And Label51 = "PE-RT16" Then attribuut.TextString = "PE-RT 16*2 mm"
''        If attribuut.TagString = "U_TOTAALPE16" And attribuut.TextString = "" Then attribuut.TextString = TextBox46 'TOTAAL AANTAL GROEPEN
        
        If CheckBox1.Value = False Then
        '--PERT 16*2
        If attribuut.TagString = "U_WTH16120" And attribuut.textstring = "" Then attribuut.textstring = TextBox43 '120 METER
        If attribuut.TagString = "U_WTH1690" And attribuut.textstring = "" Then attribuut.textstring = TextBox44 '90 METER
        If attribuut.TagString = "U_WTH1660" And attribuut.textstring = "" Then attribuut.textstring = TextBox45 '60 METER
        If attribuut.TagString = "U_TOTAALPE16" And attribuut.textstring = "" Then attribuut.textstring = TextBox46 'TOTAAL PERT
        Else '---+ 800 meter
        If attribuut.TagString = "U_WTH16800" And attribuut.textstring = "" Then attribuut.textstring = TextBox61 '800 METER
        If attribuut.TagString = "U_WTH16120" And attribuut.textstring = "" Then attribuut.textstring = TextBox57 '120 METER
        If attribuut.TagString = "U_WTH1690" And attribuut.textstring = "" Then attribuut.textstring = TextBox58 '90 METER
        If attribuut.TagString = "U_WTH1660" And attribuut.textstring = "" Then attribuut.textstring = TextBox59 '60 METER
        If attribuut.TagString = "U_TOTAALPE16" And attribuut.textstring = "" Then attribuut.textstring = TextBox60 'TOTAAL PERT
        End If
        
        '--PE 14
        If attribuut.TagString = "U_WTH1490" And attribuut.textstring = "" Then attribuut.textstring = TextBox52 '90 METER
        If attribuut.TagString = "U_WTH1460" And attribuut.textstring = "" Then attribuut.textstring = TextBox53 '60 METER
       ' If attribuut.TagString = "PERT" And attribuut.TextString = "" And Label52 = "PE-RT14" Then attribuut.TextString = "PE-RT 14*2 mm"
        If attribuut.TagString = "U_TOTAALPE14" And attribuut.textstring = "" Then attribuut.textstring = TextBox54 'TOTAAL AANTAL GROEPEN
       
       Next m
       
       End If
      End If
     End If
  Next element
 
 
 For Each element In ThisDrawing.ModelSpace
      If element.ObjectName = "AcDbBlockReference" Then
      If element.Name = "unitlogo_extragroepen" Then
      Set symbool = element
        If symbool.HasAttributes Then
        attributen = symbool.GetAttributes
        For k = LBound(attributen) To UBound(attributen)
        Set attribuut = attributen(k)
        If attribuut.TagString = "U_REGELUNITTYPE11" And attribuut.textstring = "" Then attribuut.textstring = TextBox26 'REGELUNIT11
        If attribuut.TagString = "U_REGELUNITTYPE12" And attribuut.textstring = "" Then attribuut.textstring = TextBox27 'REGELUNIT12
        If attribuut.TagString = "U_REGELUNITTYPE13" And attribuut.textstring = "" Then attribuut.textstring = TextBox28 'REGELUNIT13
        If attribuut.TagString = "U_REGELUNITTYPE14" And attribuut.textstring = "" Then attribuut.textstring = TextBox29 'REGELUNIT14
        If attribuut.TagString = "U_REGELUNITTYPE15" And attribuut.textstring = "" Then attribuut.textstring = TextBox30 'REGELUNIT15
        If attribuut.TagString = "U_REGELUNITTYPE16" And attribuut.textstring = "" Then attribuut.textstring = TextBox31 'REGELUNIT16
               
        If attribuut.TagString = "U_BEVESTIGINGSTYPE11" And attribuut.textstring = "" Then attribuut.textstring = TextBox34 'BEVESTIGING11
        If attribuut.TagString = "U_BEVESTIGINGSTYPE12" And attribuut.textstring = "" Then attribuut.textstring = TextBox35 'BEVESTIGING12
        If attribuut.TagString = "U_BEVESTIGINGSTYPE13" And attribuut.textstring = "" Then attribuut.textstring = TextBox36 'BEVESTIGING13
        If attribuut.TagString = "U_BEVESTIGINGSTYPE14" And attribuut.textstring = "" Then attribuut.textstring = TextBox37 'BEVESTIGING14
        If attribuut.TagString = "U_BEVESTIGINGSTYPE15" And attribuut.textstring = "" Then attribuut.textstring = TextBox38 'BEVESTIGING15
        If attribuut.TagString = "U_BEVESTIGINGSTYPE16" And attribuut.textstring = "" Then attribuut.textstring = TextBox39 'BEVESTIGING16
               
        Next k
       
       End If
      End If
     End If
  Next element
 'End If
 
 For Each element In ThisDrawing.ModelSpace
      If element.ObjectName = "AcDbBlockReference" Then
      If element.Name = "unitlogo_FLEX" Then
      Set symbool = element
        If symbool.HasAttributes Then
        attributen = symbool.GetAttributes
        For t = LBound(attributen) To UBound(attributen)
        Set attribuut = attributen(t)
        If attribuut.TagString = "FLEXMATTEN" And attribuut.textstring = "" Then attribuut.textstring = TextBox55 'AANTAL MATTEN
        If attribuut.TagString = "FLEXMEET_TOTAAL" And attribuut.textstring = "" Then attribuut.textstring = TextBox56 'AANTAL METER
        Next t
       End If
      End If
     End If
  Next element
 
 
 
 Unload Me
End Sub
Sub Schaal(scaal)
frmUnitlogo.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
Update
End Sub
Private Sub cmdAfsluiten_Click()
Unload Me
End Sub

Attribute VB_Name = "frmWaarschuwing"
Attribute VB_Base = "0{00B4F7FD-0D2D-4EFF-95C4-7E6D9F830F49}{06164326-7B11-490C-BB9A-1040E78E37F5}"
Attribute VB_GlobalNameSpace = False
Attribute VB_Creatable = False
Attribute VB_PredeclaredId = True
Attribute VB_Exposed = False
Attribute VB_TemplateDerived = False
Attribute VB_Customizable = False
#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000



Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
  
frmWaarschuwing.TextBox1 = frmGroeptekst.TextBox2
frmWaarschuwing.TextBox2 = frmGroeptekst.TextBox9

If frmGroeptekst.ToggleButton2.Value = True Then Call togglemodule.groeptekst_waarschuwing_toggle

Call ZOEK_DE_FOUT
End Sub
Sub ZOEK_DE_FOUT()
unittel = frmGroeptekst.TextBox9

If unittel > 0 And unittel < 10 Then
  unitonder10 = "0" & frmGroeptekst.TextBox9
Else
  unitonder10 = frmGroeptekst.TextBox9
End If

For Each element In ThisDrawing.ModelSpace
      If element.ObjectName = "AcDbBlockReference" Then
      If element.Name = "groeptekstbloknew" Or element.Name = "GROEPTEKSTBLOKNEW" Then

      
      Set symbool = element
        If symbool.HasAttributes Then
        attributen = symbool.GetAttributes
        For I = LBound(attributen) To UBound(attributen)
        Set attribuut = attributen(I)
           If UCase(attribuut.TagString) = "UNITNUMMER" And attribuut.textstring <> "" Then bb = attribuut.textstring 'REGELUNITNUMMER
           If UCase(attribuut.TagString) = "ROLLENGTE" And attribuut.textstring = "165 meter" Then zdf = attribuut.textstring
           If UCase(attribuut.TagString) = "GROEPTEKST" And attribuut.textstring <> "" Then gpt = attribuut.textstring
                
                  If bb = unitonder10 And zdf = "165 meter" Then
                  
                        
                        
                        
                     For Each element2 In ThisDrawing.ModelSpace
                        If element2.Layer = gpt Then
                        'BEREKENEN TOTALE LENGTE
                          If element2.EntityName = "AcDbLine" Then Lengte = Lengte + element2.Length
                          If element2.EntityName = "AcDbArc" Then Lengte = Lengte + element2.ArcLength
                        End If
                       Next element2
                       z = 0
                       Dim cirkel As Object
                       For Each cirkel In ThisDrawing.ModelSpace
                          If cirkel.Layer = gpt Then
                          If cirkel.EntityName = "AcDbCircle" Then z = z + 1
                          End If
                          Next cirkel
                          
                      If frmGroeptekst.ToggleButton1.Value = False Then wandhoogte = 2.5
                      If frmGroeptekst.ToggleButton1.Value = True Then wandhoogte = 2
                      If frmGroeptekst.OptionButton5 = True Then wandhoogte = frmGroeptekst.TextBox13
                          
                          If z <> 0 Then zlengte = (z * (100 * wandhoogte)) + 100
              
                      Lengte = Lengte + zlengte
                    
                     'LENGTE IN METERS
                      Lengte = Lengte / 100
                      Lengte = Round(Lengte, 1)
                      Lengte = Lengte ' + 3 ' 07-04-06
                      LLL = gpt & " = " & Lengte & " meter."
                      
                      If frmGroeptekst.ToggleButton2.Value = True Then ''''''''''''engeland
                             lp = Split(LLL, " ") ''''''''''''engeland
                             LLL = "group " & lp(1) & " = " & Lengte & " meter." ''''''''''''engeland
                      End If ''''''''''''engeland
                             
                             
                             
                      If zdf = "165 meter" Then ListBox1.AddItem (LLL)
                       
                       Lengte = 0
                       zdf = ""
                       bb = ""
                       gpt = ""
             
                   End If 'BB
           Next I
       
        End If
      End If
      End If
  Next element
End Sub

Private Sub cmdnietsveranderen_Click()
Unload Me
frmGroeptekst.TextBox2.BackColor = &HFFFFFF
End Sub
Private Sub cmdwijzigen_Click()
Unload Me
frmGroeptekst.TextBox2.BackColor = &HFFFFFF
b = Val(frmGroeptekst.TextBox2)
frmGroeptekst.TextBox2 = "0"
frmGroeptekst.TextBox3 = Val(frmGroeptekst.TextBox3) + b 'Val(frmGroeptekst.TextBox2)

unittel = frmGroeptekst.TextBox9

If unittel > 0 And unittel < 10 Then
  unitonder10 = "0" & frmGroeptekst.TextBox9
Else
  unitonder10 = frmGroeptekst.TextBox9
End If


For Each element In ThisDrawing.ModelSpace
      If element.ObjectName = "AcDbBlockReference" Then
      If element.Name = "groeptekstbloknew" Or element.Name = "GROEPTEKSTBLOKNEW" Then
      
      Set symbool = element
        If symbool.HasAttributes Then
        attributen = symbool.GetAttributes
        For I = LBound(attributen) To UBound(attributen)
        Set attribuut = attributen(I)
        If UCase(attribuut.TagString) = "UNITNUMMER" And attribuut.textstring <> "" Then bb = attribuut.textstring 'REGELUNITNUMMER
            If bb = unitonder10 Then
              For k = LBound(attributen) To UBound(attributen)
              Set attribuut = attributen(k)
       
                 If UCase(attribuut.TagString) = "ROLLENGTE" And attribuut.textstring = "165 meter" Then attribuut.textstring = "125 meter"
                 
             Next k
             bb = ""
             End If
       Next I
       
        End If
      End If
      End If
  Next element

Update

End Sub

Attribute VB_Name = "togglemodule"
Sub groeptekst_dutch()
frmGroeptekst.Caption = "GROEPTEKST PLAATSEN  [proefversie A]"
frmGroeptekst.Frame1.Caption = "Rollengte's"
frmGroeptekst.Frame2.Caption = "Groeptekst"
frmGroeptekst.Frame3.Caption = "Unitlogo"
frmGroeptekst.Frame4.Caption = "Wandhoogte"
frmGroeptekst.Frame5.Caption = "Groep en unitlogo"
frmGroeptekst.Frame6.Caption = "Groep-range verwijderen"
frmGroeptekst.Label8.Caption = "Unit"
frmGroeptekst.Label9.Caption = "Groepsnummer"
frmGroeptekst.Label12.Caption = "Type unit"
frmGroeptekst.Label13.Caption = "Type regeling"
frmGroeptekst.Label14.Caption = "Bevestiging"
frmGroeptekst.Label26.Caption = "Type buis"
frmGroeptekst.Label23.Caption = "Unitnummer"
frmGroeptekst.Label29.Caption = "Extra groepen"
frmGroeptekst.Label34.Caption = "Unitnummer"
frmGroeptekst.Label35.Caption = "van groepsnummer"
frmGroeptekst.Label36.Caption = "t/m groepsnummer"
frmGroeptekst.Label37.Caption = "Totaal Flexfix"
frmGroeptekst.Label38.Caption = "Aantal matten"
frmGroeptekst.CheckBox2.Caption = "Werkelijke rollengte"
frmGroeptekst.cmdAfsluiten.Caption = "Afsluiten"
frmGroeptekst.CmdBloklogo.Caption = "Unitlogo"
frmGroeptekst.CmdErase.Caption = "Verwijder groeptekst"
frmGroeptekst.Cmdmeten.Caption = "Meet de groep"
frmGroeptekst.cmdTelrollen.Caption = "Aantal rollen tellen"
frmGroeptekst.CommandButton4.Caption = "Verwijder lege groep- & wandlayers"
frmGroeptekst.CommandButton5.Caption = "Verwijder groeptekst"
frmGroeptekst.CommandButton6.Caption = "Unitlogo bijwerken"
frmGroeptekst.CheckBox1.Caption = "Variabele rollengte"
frmGroeptekst.CheckBox7.Caption = "Afwijkende A&R"
frmGroeptekst.Label40.Caption = "Restlengte"
frmGroeptekst.TextBox13.ControlTipText = "EEN PUNT GEBRUIKEN (GEEN KOMMA)"
frmGroeptekst.TextBox24.ControlTipText = "Vul hier de totale restlengte in. (restlengte = A en  R)"
frmGroeptekst.TextBox28.ControlTipText = "Restlengte (= aanvoer EN retour)"
frmGroeptekst.OptionButton5.Caption = "Variabel"
frmGroeptekst.OptionButton7.Caption = "Ringleiding"

End Sub
Sub groeptekst_english()
frmGroeptekst.Caption = "PLACE GROUPTEXT [proefversie A]"
frmGroeptekst.Frame1.Caption = "Roll length"
frmGroeptekst.Frame2.Caption = "Grouptext"
frmGroeptekst.Frame3.Caption = "Manifold logo"
frmGroeptekst.Frame4.Caption = "Wall height"
frmGroeptekst.Frame5.Caption = "Group/Manifold"
frmGroeptekst.Frame6.Caption = "Delete group-range"
frmGroeptekst.Label8.Caption = "Manifold"
frmGroeptekst.Label9.Caption = "Groupnumber"
frmGroeptekst.Label12.Caption = "Manifold type"
frmGroeptekst.Label13.Caption = "Control type"
frmGroeptekst.Label14.Caption = "Fixing material"
frmGroeptekst.Label26.Caption = "Tube type"
frmGroeptekst.Label23.Caption = "Manifold"
frmGroeptekst.Label29.Caption = "Extra groups"
frmGroeptekst.Label34.Caption = "Manifold"
frmGroeptekst.Label35.Caption = "from groupnumber"
frmGroeptekst.Label36.Caption = "including groupnumber"
frmGroeptekst.Label37.Caption = "Total Flexfix"
frmGroeptekst.Label38.Caption = "Amount mats"
frmGroeptekst.CheckBox2.Caption = "True roll length"
frmGroeptekst.cmdAfsluiten.Caption = "Close"
frmGroeptekst.CmdBloklogo.Caption = "Manifold logo"
frmGroeptekst.CmdErase.Caption = "Delete grouptext"
frmGroeptekst.Cmdmeten.Caption = "Measure the group"
frmGroeptekst.cmdTelrollen.Caption = "Count the groups"
frmGroeptekst.CommandButton4.Caption = "Delete empty grouplayers"
frmGroeptekst.CommandButton5.Caption = "Delete grouptext"
frmGroeptekst.CommandButton6.Caption = "Update Manifold logo"
frmGroeptekst.CheckBox1.Caption = "Variable roll length"
frmGroeptekst.CheckBox7.Caption = "Different flow & return"
frmGroeptekst.Label40.Caption = "Rest length"
frmGroeptekst.TextBox13.ControlTipText = "USE A COMMA TO SEPARATE FIGURES (EXAMPLE: 2,4 and not 2.4)"
frmGroeptekst.TextBox24.ControlTipText = "Fill in the rest length (flow and return)"
frmGroeptekst.TextBox28.ControlTipText = "Rest length. (flow and return)"
frmGroeptekst.OptionButton5.Caption = "Variable"
frmGroeptekst.OptionButton7.Caption = "Loop"
End Sub
Sub groeptekst_combolijst5()
frmGroeptekst.ComboBox1.Clear
frmGroeptekst.ComboBox1.AddItem "Sack tie"
frmGroeptekst.ComboBox1.AddItem "Hammerclips"
frmGroeptekst.ComboBox1.AddItem "Nails"
frmGroeptekst.ComboBox1.AddItem "IFD Cardboard"
frmGroeptekst.ComboBox1.AddItem "IFD Polystyrene"
frmGroeptekst.ComboBox1.AddItem "Isoclips"
frmGroeptekst.ComboBox1.AddItem "Wedge"
frmGroeptekst.ComboBox1.AddItem "Tiewrap"
frmGroeptekst.ComboBox1.AddItem "Varisoclips"
End Sub
Sub groeptekst_waarschuwing_toggle()
frmWaarschuwing.Label1.Caption = "roll(s) on manifold"
frmWaarschuwing.Label2.Caption = " is/are 165 meter"
frmWaarschuwing.cmdnietsveranderen.Caption = " Correct, no changes"
frmWaarschuwing.cmdwijzigen.Caption = " Change the roll length to 125 meter"
frmWaarschuwing.Caption = "Caution"
End Sub

Sub kaderlogo_english()
frmKaderlogo.Caption = "Framework logo"
frmKaderlogo.Frame1.Caption = "Client & Project information"
frmKaderlogo.Frame2.Caption = "Alterations"
frmKaderlogo.cmdAfsluiten.Caption = "Close"
frmKaderlogo.cmdAfsluiten.Accelerator = "C"
frmKaderlogo.CmdUpdate.ControlTipText = "Fill in or change the framework logo"
frmKaderlogo.cmdAfsluiten.ControlTipText = "Close window"
frmKaderlogo.ToggleButton1.ControlTipText = "Show/hide the alterations"
frmKaderlogo.Label42.Caption = "Client": frmKaderlogo.Label41.Caption = "Sheet": frmKaderlogo.Label48.Caption = "Alt. a"
frmKaderlogo.Label43.Caption = "Location": frmKaderlogo.Label40.Caption = "Size": frmKaderlogo.Label49.Caption = "Alt. b"
frmKaderlogo.Label45.Caption = "Description": frmKaderlogo.Label39.Caption = "Name": frmKaderlogo.Label50.Caption = "Alt.c"
frmKaderlogo.Label44.Caption = "Instal.Adress": frmKaderlogo.Label38.Caption = "Scale": frmKaderlogo.Label51.Caption = "Alt. d"
frmKaderlogo.Label46.Caption = "Instal.Location ": frmKaderlogo.Label37.Caption = "Date": frmKaderlogo.Label52.Caption = "Alt. e"
frmKaderlogo.Label47.Caption = "Project": frmKaderlogo.Label55.Caption = "Revision": frmKaderlogo.Label53.Caption = "Alt. f"
frmKaderlogo.Label54.Caption = "Alt. g"
frmKaderlogo.TextBox1.ControlTipText = "The name of the client": frmKaderlogo.TextBox2.ControlTipText = "Place of the client"
frmKaderlogo.TextBox3.ControlTipText = "The name of the project": frmKaderlogo.TextBox4.ControlTipText = "Installation adress"
frmKaderlogo.TextBox5.ControlTipText = "Installation location": frmKaderlogo.TextBox6.ControlTipText = "Projectnumber"
frmKaderlogo.TextBox8.ControlTipText = "Size of the drawing": frmKaderlogo.TextBox9.ControlTipText = "Name of the draftsman"
frmKaderlogo.TextBox10.ControlTipText = "Scale": frmKaderlogo.TextBox11.ControlTipText = "Sign date"
frmKaderlogo.TextBox12.ControlTipText = "Alteration 1": frmKaderlogo.TextBox13.ControlTipText = "Alteration 2"
frmKaderlogo.TextBox14.ControlTipText = "Alteration 3": frmKaderlogo.TextBox15.ControlTipText = "Alteration 4"
frmKaderlogo.TextBox16.ControlTipText = "Alteration 5": frmKaderlogo.TextBox17.ControlTipText = "Alteration 6"
frmKaderlogo.TextBox18.ControlTipText = "Alteration 7"
frmKaderlogo.ComboBox1.ControlTipText = "Sheet number"
End Sub
Sub kaderlogo_dutch()
frmKaderlogo.Caption = "Kaderlogo"
frmKaderlogo.Frame1.Caption = "Invulgegevens klant"
frmKaderlogo.Frame2.Caption = "Wijzigingen"
frmKaderlogo.cmdAfsluiten.Caption = "Afsluiten"
frmKaderlogo.cmdAfsluiten.Accelerator = "A"
frmKaderlogo.CmdUpdate.ControlTipText = "Kaderlogo invullen of wijzigen"
frmKaderlogo.cmdAfsluiten.ControlTipText = "Venster sluiten"
frmKaderlogo.ToggleButton1.ControlTipText = "Hiermee komen de wijzigingsdatums te voorschijn"
frmKaderlogo.Label42.Caption = "Opdrachtgever": frmKaderlogo.Label41.Caption = "Blad": frmKaderlogo.Label48.Caption = "Wijziging a"
frmKaderlogo.Label43.Caption = "Plaats": frmKaderlogo.Label40.Caption = "Formaat": frmKaderlogo.Label49.Caption = "Wijziging b"
frmKaderlogo.Label45.Caption = "Projectnaam": frmKaderlogo.Label39.Caption = "Tekenaar": frmKaderlogo.Label50.Caption = "Wijziging c"
frmKaderlogo.Label44.Caption = "Montageadres": frmKaderlogo.Label38.Caption = "Schaal": frmKaderlogo.Label51.Caption = "Wijziging d"
frmKaderlogo.Label46.Caption = "Montageplaats": frmKaderlogo.Label37.Caption = "Datum": frmKaderlogo.Label52.Caption = "Wijziging e"
frmKaderlogo.Label47.Caption = "Projectnummer": frmKaderlogo.Label55.Caption = "Revisie": frmKaderlogo.Label53.Caption = "Wijziging f"
frmKaderlogo.Label54.Caption = "Wijziging g"
frmKaderlogo.TextBox1.ControlTipText = "Vul naam van de opdrachtgever in": frmKaderlogo.TextBox2.ControlTipText = "Plaats v/d opdr.gever"
frmKaderlogo.TextBox3.ControlTipText = "Vul projectnaam in": frmKaderlogo.TextBox4.ControlTipText = "Vul montage adres in"
frmKaderlogo.TextBox5.ControlTipText = "Vul montageplaats in": frmKaderlogo.TextBox6.ControlTipText = "Projectnummer"
frmKaderlogo.TextBox8.ControlTipText = "Formaat v/d tekening": frmKaderlogo.TextBox9.ControlTipText = "Tekenaar"
frmKaderlogo.TextBox10.ControlTipText = "Schaal": frmKaderlogo.TextBox11.ControlTipText = "Tekendatum"
frmKaderlogo.TextBox12.ControlTipText = "Wijzigingsdatum 1": frmKaderlogo.TextBox13.ControlTipText = "Wijzigingsdatum 2"
frmKaderlogo.TextBox14.ControlTipText = "Wijzigingsdatum 3": frmKaderlogo.TextBox15.ControlTipText = "Wijzigingsdatum 4"
frmKaderlogo.TextBox16.ControlTipText = "Wijzigingsdatum 5": frmKaderlogo.TextBox17.ControlTipText = "Wijzigingsdatum 6"
frmKaderlogo.TextBox18.ControlTipText = "Wijzigingsdatum 7"
frmKaderlogo.ComboBox1.ControlTipText = "Bladnummer"
End Sub
