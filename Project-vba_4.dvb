Attribute VB_Name = "Module1"
Sub change2background()
frmChange2BackGround.show
End Sub

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
Option Explicit

Sub change2background()
  
  Call frmChange2BackGround.show(vbModal)

End Sub

Attribute VB_Name = "frmChange2BackGround"
Attribute VB_Base = "0{5BD5FDD3-4679-47F0-AFC8-D3BC8EC7E465}{9726E203-085E-4F74-A337-77AD6D511D5C}"
Attribute VB_GlobalNameSpace = False
Attribute VB_Creatable = False
Attribute VB_PredeclaredId = True
Attribute VB_Exposed = False
Attribute VB_TemplateDerived = False
Attribute VB_Customizable = False
' VBA Macro: Prepare Selected Drawings as Background
' Fully compatible with 64-bit AutoCAD + modern systems
' Updated to behave exactly like the legacy VBA form version
' Requires: Microsoft Office XX.0 Object Library enabled (Tools > References)

Option Explicit

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" (ByVal hWnd As Long) As Long
    Private Declare Function GetMenuItemCount Lib "user32" (ByVal hMenu As Long) As Long
    Private Declare Function GetSystemMenu Lib "user32" (ByVal hWnd As Long, ByVal bRevert As Long) As Long
    Private Declare Function RemoveMenu Lib "user32" (ByVal hMenu As Long, ByVal nPosition As Long, ByVal wFlags As Long) As Long
#End If

Private Const MF_BYPOSITION = &H400
Private Const MF_REMOVE = &H1000

Dim mstrPath As String
Dim mappAcad As AcadApplication

Private Sub UserForm_Initialize()
#If VBA7 Then
    Dim lngHwnd As LongPtr
    Dim lngMenu As LongPtr
#Else
    Dim lngHwnd As Long
    Dim lngMenu As Long
#End If
    Dim lngCnt As Long
    lngHwnd = FindWindow(vbNullString, Me.Caption)
    lngMenu = GetSystemMenu(lngHwnd, 0)
    If lngMenu Then
        lngCnt = GetMenuItemCount(lngMenu)
        Call RemoveMenu(lngMenu, lngCnt - 1, MF_REMOVE Or MF_BYPOSITION)
        Call DrawMenuBar(lngHwnd)
    End If

    Set mappAcad = GetObject(, "AutoCAD.Application")

    With Me.cboColors
        .AddItem "242"
        .AddItem "250"
        .AddItem "251"
        .AddItem "252"
        .AddItem "253"
        .AddItem "254"
        .AddItem "255"
        .ListIndex = 5
    End With
End Sub

Private Sub cmdClose_Click()
    Unload Me
End Sub

Private Sub UserForm_Terminate()
    Set mappAcad = Nothing
End Sub

Private Sub cmdSelect_Click()
    Dim sh As Object
    Dim folder As Object
    Dim item As Object
    Dim path As String
    Dim strFileName As String

    Set sh = CreateObject("Shell.Application")
    Set folder = sh.BrowseForFolder(0, "Select Folder with DWG files", 0, 0)

    If Not folder Is Nothing Then
        path = folder.Self.path
        If Right(path, 1) <> "\" Then path = path & "\"
        mstrPath = path
        lstDrawings.Clear

        strFileName = Dir(path & "*.dwg")
        Do While strFileName <> ""
            lstDrawings.AddItem strFileName
            strFileName = Dir
        Loop
    End If
End Sub


Private Sub cmdStart_Click()
    Dim intDrawing As Integer
    If lstDrawings.ListCount = 0 Then
        MsgBox "No drawings selected.", vbExclamation
        Exit Sub
    End If
    For intDrawing = 0 To lstDrawings.ListCount - 1
        PrepareAsBackGround mstrPath & lstDrawings.List(intDrawing), cboColors.Value
    Next intDrawing
    Unload Me
    MsgBox "All drawings processed successfully.", vbInformation
End Sub

Private Sub CommandButton1_Click()
    Dim ACADPref As AcadPreferencesOpenSave
    Dim originalValue As Variant, DisplayValue As String

    Set ACADPref = ThisDrawing.Application.Preferences.OpenSave
    originalValue = ACADPref.SaveAsType

    GoSub GETVALUE
    MsgBox "Current SaveAsType: " & DisplayValue

    ACADPref.SaveAsType = ac2000_dwg
    GoSub GETVALUE
    MsgBox "Changed SaveAsType to: " & DisplayValue

    ACADPref.SaveAsType = originalValue
    GoSub GETVALUE
    MsgBox "Reset SaveAsType back to: " & DisplayValue

    Exit Sub

GETVALUE:
    DisplayValue = ACADPref.SaveAsType
    Select Case DisplayValue
        Case ac2000_dwg:  DisplayValue = "AutoCAD 2000 DWG (*.dwg)"
        Case ac2000_dxf:  DisplayValue = "AutoCAD 2000 DXF (*.dxf)"
        Case ac2000_Template: DisplayValue = "AutoCAD 2000 DWT"
        Case ac2004_dwg:  DisplayValue = "AutoCAD 2004 DWG (*.dwg)"
        Case ac2004_dxf:  DisplayValue = "AutoCAD 2004 DXF (*.dxf)"
        Case ac2004_Template: DisplayValue = "AutoCAD 2004 DWT"
        Case ac2007_dwg:  DisplayValue = "AutoCAD 2007 DWG (*.dwg)"
        Case acNative:    DisplayValue = "Latest Drawing Format"
        Case acUnknown:   DisplayValue = "Unknown Type"
    End Select
    Return
End Sub

Sub PrepareAsBackGround(strDrawingFullname As String, colorValue As String)
    Dim objDocument As AcadDocument
    Dim objBlock As AcadBlock
    Dim objEntity As AcadEntity
    Dim objLayer As AcadLayer
    Dim strSaveAs As String
    Dim lngColor As Long

    If Len(Dir(strDrawingFullname)) = 0 Then Exit Sub
    Set objDocument = mappAcad.Documents.Open(strDrawingFullname)

    With objDocument
        strSaveAs = .path & "\Calculatie_" & .Name
        .SaveAs strSaveAs, acNative
        .AuditInfo True
        .PurgeAll
        ThisDrawing.SendCommand "burst" & vbCr & "all" & vbCr & vbCr

        For Each objBlock In .Blocks
            If objBlock.IsXRef Then objBlock.Bind True
        Next objBlock

        Set objLayer = .Layers.Add("Bouwkundig")
        objLayer.color = 254
        objLayer.Linetype = "Continuous"
        objLayer.Lineweight = acLnWtByLwDefault
        objLayer.Lock = False

        lngColor = CLng(colorValue)
        For Each objLayer In .Layers
            objLayer.color = lngColor
            objLayer.Lineweight = acLnWtByLwDefault
            objLayer.Lock = False
        Next objLayer

        For Each objEntity In .ModelSpace
            objEntity.layer = "Bouwkundig"
            objEntity.color = acByLayer
            objEntity.Lineweight = acLnWtByLwDefault
        Next objEntity

        For Each objEntity In .ModelSpace
            Select Case objEntity.ObjectName
                Case "AcDbDimension", "AcDbHatch", "AcDbSolid", "AcDbImage", _
                     "AcDbRotatedDimension", "AcDbAlignedDimension", "AcDbAngularDimension"
                    objEntity.Delete
            End Select
        Next objEntity

        .PurgeAll
        .Close True
    End With
    Set objDocument = Nothing
End Sub

Attribute VB_Name = "frmtextreplace"
Attribute VB_Base = "0{37EE2E43-F39A-41D4-B275-9378657C674B}{EB4BED47-D6CD-45B6-9537-9FDE6569EB08}"
Attribute VB_GlobalNameSpace = False
Attribute VB_Creatable = False
Attribute VB_PredeclaredId = True
Attribute VB_Exposed = False
Attribute VB_TemplateDerived = False
Attribute VB_Customizable = False
' VBA Macro: Prepare DWG Text Replacement Tool (Updated for 64-bit)
' Fully compatible with AutoCAD 2020+ and modern systems
' Mimics exact behavior of original VBA logic
' Requires: Microsoft Office XX.0 Object Library enabled (Tools > References)

Option Explicit

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" (ByVal hWnd As Long) As Long
    Private Declare Function GetMenuItemCount Lib "user32" (ByVal hMenu As Long) As Long
    Private Declare Function GetSystemMenu Lib "user32" (ByVal hWnd As Long, ByVal bRevert As Long) As Long
    Private Declare Function RemoveMenu Lib "user32" (ByVal hMenu As Long, ByVal nPosition As Long, ByVal wFlags As Long) As Long
#End If

Private Const MF_BYPOSITION = &H400
Private Const MF_REMOVE = &H1000

Dim mappAcad As AcadApplication
Dim mstrPath As String

Private Sub UserForm_Initialize()
#If VBA7 Then
    Dim lngHwnd As LongPtr
    Dim lngMenu As LongPtr
#Else
    Dim lngHwnd As Long
    Dim lngMenu As Long
#End If
    Dim lngCnt As Long
    lngHwnd = FindWindow(vbNullString, Me.Caption)
    lngMenu = GetSystemMenu(lngHwnd, 0)
    If lngMenu Then
        lngCnt = GetMenuItemCount(lngMenu)
        Call RemoveMenu(lngMenu, lngCnt - 1, MF_REMOVE Or MF_BYPOSITION)
        Call DrawMenuBar(lngHwnd)
    End If
    Set mappAcad = GetObject(, "AutoCAD.Application")
End Sub

Private Sub TextBox1_Change()
    cmdStart.Enabled = (TextBox1 <> "" And TextBox2 <> "")
End Sub

Private Sub TextBox2_Change()
    cmdStart.Enabled = (TextBox1 <> "" And TextBox2 <> "")
End Sub

Private Sub CommandButton1_Click()
    lstDrawings.Clear
    ListBox1.Clear
End Sub

Private Sub cmdClose_Click()
    Unload Me
End Sub

Private Sub UserForm_Terminate()
    Set mappAcad = Nothing
End Sub

Private Sub cmdSelect_Click()
    Dim fd As FileDialog
    Dim selectedFile As Variant
    Dim strFileName As String

    Set fd = Application.FileDialog(msoFileDialogFilePicker)
    With fd
        .Title = "Select DWG Files"
        .Filters.Clear
        .Filters.Add "AutoCAD Drawings", "*.dwg"
        .AllowMultiSelect = True
        .InitialFileName = "F:\\Fserver2\\Gegevens\\Projecten\\"
        If .show = -1 Then
            lstDrawings.Clear
            ListBox1.Clear
            For Each selectedFile In .SelectedItems
                mstrPath = Left(selectedFile, InStrRev(selectedFile, "\\"))
                strFileName = Mid(selectedFile, InStrRev(selectedFile, "\\") + 1)
                lstDrawings.AddItem strFileName
                ListBox1.AddItem mstrPath
            Next selectedFile
        End If
    End With
End Sub

Private Sub cmdStart_Click()
    Dim i As Integer
    If lstDrawings.ListCount = 0 Then Exit Sub
    For i = 0 To lstDrawings.ListCount - 1
        Call PrepareAsBackGround(ListBox1.List(i) & lstDrawings.List(i))
    Next i
    Unload Me
End Sub

Sub PrepareAsBackGround(strDrawingFullname As String)
    Dim objDocument As AcadDocument
    Dim ori As String, verv As String

    If FileExists(strDrawingFullname) Then
        Set objDocument = mappAcad.Documents.Open(strDrawingFullname)
        ori = TextBox1
        verv = TextBox2
        ThisDrawing.SendCommand "srxtext" & vbCr & "R" & vbCr & ori & vbCr & verv & vbCr & "A" & vbCr & "A" & vbCr & "R" & vbCr
        objDocument.Close SaveChanges:=True
        Set objDocument = Nothing
    End If
End Sub

Private Function FileExists(strFullFilename As String) As Boolean
    If Len(strFullFilename) <> 0 Then
        FileExists = (Len(Dir(strFullFilename, vbNormal)) <> 0)
    End If
End Function
