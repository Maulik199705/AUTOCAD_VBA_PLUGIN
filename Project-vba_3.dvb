Attribute VB_Name = "Calc_Check_Kaderlogo"
'checken of er meerdere kaderlogocalc's in de tekening staan
Sub Check_kaderlogocalc()

Dim element As Object
For Each element In ThisDrawing.ModelSpace
      If element.ObjectName = "AcDbBlockReference" Then
         If element.Name = "kaderlogocalc" Then a = a + 1
      End If
Next element
      
      
If a > 1 Then

For Each element In ThisDrawing.ModelSpace
      If element.ObjectName = "AcDbBlockReference" Then
       If UCase(element.Name) = "KADERLOGOCALC" Then
       Set symbool = element
        If symbool.HasAttributes Then
        attributen = symbool.GetAttributes
        For I = LBound(attributen) To UBound(attributen)
        Set attribuut = attributen(I)
        If attribuut.TagString = "PROJECTNAAM" And attribuut.textstring = "" Then element.Erase
        Next I
       End If
     End If
   End If
  Next element

End If



Dim pe2(0 To 2) As Double
Dim element2
Dim insp

For Each element2 In ThisDrawing.ModelSpace
      If element2.ObjectName = "AcDbBlockReference" Then
         If element2.Name = "ba3calc" Or element2.Name = "ba2calc" Or element2.Name = "ba1calc" _
         Or element2.Name = "ba0calc" Or element2.Name = "ba0+calc" Then
          insp = element2.InsertionPoint

          pe2(0) = insp(0)
          pe2(1) = insp(1)
          pe2(2) = 0
          If pe2(0) <> 0 Or pe2(1) <> 0 Then
          MsgBox "Je kader staat niet goed...!!!", vbCritical
          element2.Erase
          Exit Sub
          End If
          'MsgBox pe2(0) & " - " & pe2(1) & " - " & pe2(2) & " - "

          End If

      End If
Next element2

End Sub

Attribute VB_Name = "Calc_Unitblok"
Sub Unitblok(scaal, pb2, bestand2)
  Set blockRefObj = ThisDrawing.ModelSpace.InsertBlock(pb2, bestand2, scaal, scaal, 1, 0)
  Update
End Sub

Attribute VB_Name = "Module1"
Sub calcblok()
frmCalculatieKaderlogo.Show
End Sub
Sub calcunit()
frmCalcUnit.Show
End Sub

Attribute VB_Name = "Update_calcmodule"
Sub update_unitlogo_calc()
On Error Resume Next
If frmGroeptekst.ComboBox2 = "" Then
    MsgBox "Je bent 'Type unit' vergeten in te vullen..!!"
    frmGroeptekst.ComboBox2.SetFocus
    Exit Sub
    End If
If frmGroeptekst.ComboBox1 = "" Then
    MsgBox "Je bent 'Bevestigingsmateriaal' vergeten in te vullen..!!"
    frmGroeptekst.ComboBox1.SetFocus
    Exit Sub
    End If
If frmGroeptekst.ComboBox4 = "" And frmGroeptekst.OptionButton6 = True Then
    MsgBox "Je bent 'Type buis' vergeten in te vullen..!!"
    frmGroeptekst.ComboBox4.SetFocus
    Exit Sub
    End If
If frmGroeptekst.ComboBox4 = "" And frmGroeptekst.OptionButton2 = True Then
    MsgBox "Je bent 'Type buis' vergeten in te vullen..!!"
    frmGroeptekst.ComboBox4.SetFocus
    Exit Sub
    End If
frmGroeptekst.Hide
frmGroeptekst.TextBox9.Locked = False
    Set newLayer = ThisDrawing.Layers.Add("BLOKLOGO")
    ThisDrawing.ActiveLayer = newLayer
    Update
    ThisDrawing.SendCommand "-layer" & vbCr & "U" & vbCr & "*" & vbCr & vbCr
    Update
Call frmGroeptekst.Schaal(scaal)
If frmGroeptekst.OptionButton1.Value = True And (frmGroeptekst.TextBox11 = "0" And frmGroeptekst.TextBox25 <> "0") Then
bestand = "c:\acad2002\dwg\Mat_spe_FLEX.dwg"
'MsgBox bestand
Else
bestand = "c:\acad2002\dwg\Mat_spe_ZD.dwg"
End If


unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If


For Each element10 In ThisDrawing.ModelSpace
      If element10.ObjectName = "AcDbBlockReference" Then
       If UCase(element10.Name) = "HERZ" Or UCase(element10.Name) = "KMV" Or UCase(element10.Name) = "RUH-N" _
       Or UCase(element10.Name) = "RUH-R" Or UCase(element10.Name) = "RUH-RT" Or UCase(element10.Name) = "RUB-R" _
       Or UCase(element10.Name) = "RUB-RT" Or UCase(element10.Name) = "RUBK-R" Or UCase(element10.Name) = "RUBK-RT" _
       Or UCase(element10.Name) = "LT" Or UCase(element10.Name) = "LT-N" Or UCase(element10.Name) = "LTS" _
       Or UCase(element10.Name) = "LT-VK" Or UCase(element10.Name) = "RINGLEIDING" Or UCase(element10.Name) = "RU-WW" _
       Or UCase(element10.Name) = "RUV" Or UCase(element10.Name) = "RUH-S" Or UCase(element10.Name) = "RUB-S" _
       Or UCase(element10.Name) = "VSKO" Or UCase(element10.Name) = "LTS-N" Or UCase(element10.Name) = "RU-WWN" _
       Or UCase(element10.Name) = "RU-WWS" Or UCase(element10.Name) = "RU-WK" Or UCase(element10.Name) = "RU-WKN" Or UCase(element10.Name) = "RU-WKS" Then
       Set symbool = element10
        If symbool.HasAttributes Then
        attributen = symbool.GetAttributes
        For I = LBound(attributen) To UBound(attributen)
        Set attribuut = attributen(I)
         If attribuut.TagString = "UNITNUMMER" And attribuut.textstring <> "" Then aa = attribuut.textstring 'UNITNUMMER
        
          If aa = unitonder10 Then
           insp = element10.InsertionPoint
           'element10.Highlight (True)
           element10.Erase
           aa = ""
          End If
        Next I
       End If
     End If
   End If
  Next element10


 
  

If frmGroeptekst.OptionButton2.Value = True Then bestand = "c:\acad2002\dwg\Mat_spe_PE.dwg"
If frmGroeptekst.OptionButton6.Value = True Then bestand = "c:\acad2002\dwg\Mat_spe_ALU.dwg"
If frmGroeptekst.OptionButton1.Value = True And (frmGroeptekst.OptionButton7 = True Or frmGroeptekst.OptionButton8 = True) Then bestand = "c:\acad2002\dwg\Mat_spe_ZDringleiding.dwg"
If frmGroeptekst.OptionButton2.Value = True And (frmGroeptekst.OptionButton7 = True Or frmGroeptekst.OptionButton8 = True) Then bestand = "c:\acad2002\dwg\Mat_spe_PEringleiding.dwg"
If frmGroeptekst.OptionButton6.Value = True And (frmGroeptekst.OptionButton7 = True Or frmGroeptekst.OptionButton8 = True) Then bestand = "c:\acad2002\dwg\Mat_spe_ALUringleiding.dwg"
bestand20 = "c:\acad2002\dwg\Mat_spe_FLEX_Aankoppel.dwg"
Update

If Err Then
    frmGroeptekst.Show
    Exit Sub
    End If
Dim element2 As Object
If frmGroeptekst.OptionButton1.Value = True Then
aantal_groepen = (Val(frmGroeptekst.TextBox1)) + (Val(frmGroeptekst.TextBox2)) + (Val(frmGroeptekst.TextBox3)) + (Val(frmGroeptekst.TextBox4)) + (Val(frmGroeptekst.TextBox5)) + _
(Val(frmGroeptekst.TextBox6)) + (Val(frmGroeptekst.TextBox7)) + (Val(frmGroeptekst.TextBox15)) + (Val(frmGroeptekst.TextBox16)) + (Val(frmGroeptekst.TextBox17))
If (Val(frmGroeptekst.TextBox1)) = 0 Then frmGroeptekst.TextBox1 = "-"
If (Val(frmGroeptekst.TextBox2)) = 0 Then frmGroeptekst.TextBox2 = "-"
If (Val(frmGroeptekst.TextBox3)) = 0 Then frmGroeptekst.TextBox3 = "-"
If (Val(frmGroeptekst.TextBox4)) = 0 Then frmGroeptekst.TextBox4 = "-"
If (Val(frmGroeptekst.TextBox5)) = 0 Then frmGroeptekst.TextBox5 = "-"
If (Val(frmGroeptekst.TextBox6)) = 0 Then frmGroeptekst.TextBox6 = "-"
If (Val(frmGroeptekst.TextBox7)) = 0 Then frmGroeptekst.TextBox7 = "-"
If (Val(frmGroeptekst.TextBox15)) = 0 Then frmGroeptekst.TextBox15 = "-"
If (Val(frmGroeptekst.TextBox16)) = 0 Then frmGroeptekst.TextBox16 = "-"
aantal_groepen = aantal_groepen + (Val(frmGroeptekst.TextBox26))
'MsgBox aantal_groepen
If frmGroeptekst.ComboBox3.Enabled = False Then
REGELTYPE = frmGroeptekst.ComboBox2 & " " & aantal_groepen 'ZONDER REGELING
Else
REGELTYPE = frmGroeptekst.ComboBox2 & " " & aantal_groepen & "/" & frmGroeptekst.ComboBox3 'met regeling
End If
If frmGroeptekst.OptionButton7 = True Or frmGroeptekst.OptionButton8 = True Then REGELTYPE = frmGroeptekst.ComboBox2

If frmGroeptekst.ComboBox2 = "RUW-Groot" Or frmGroeptekst.ComboBox2 = "RUW-Klein" Then
REGELTYPE = "RUW" & " " & aantal_groepen
End If
'bloklogo invullen WTH-ZD
  
unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element2 In ThisDrawing.ModelSpace
      If element2.ObjectName = "AcDbBlockReference" Then
      If UCase(element2.Name) = "MAT_SPE_ZD" Or UCase(element2.Name) = "MAT_SPE_ZDRINGLEIDING" Or UCase(element2.Name) = "MAT_SPE_ZD_1627" Then
      Set symbool = element2
        If symbool.HasAttributes Then
        attributen = symbool.GetAttributes
        For I = LBound(attributen) To UBound(attributen)
        Set attribuut = attributen(I)
        If attribuut.TagString = "RNU" And attribuut.textstring <> "" Then bb = attribuut.textstring 'REGELUNITNUMMER
            If bb = unitonder10 Then
              For k = LBound(attributen) To UBound(attributen)
              Set attribuut = attributen(k)
              'element2.Highlight (True)
              If attribuut.TagString = "WTHZD" And attribuut.textstring <> "" Then attribuut.textstring = "WTH-ZD 20 * 3,4 mm" 'REGELUNITNUMMER
              If attribuut.TagString = "WTH250" And attribuut.textstring <> "" Then attribuut.textstring = frmGroeptekst.TextBox1  '250 METER
              If attribuut.TagString = "WTH165" And attribuut.textstring <> "" Then attribuut.textstring = frmGroeptekst.TextBox2  '165 METER
              If attribuut.TagString = "WTH125" And attribuut.textstring <> "" Then attribuut.textstring = frmGroeptekst.TextBox3  '125 METER
              If attribuut.TagString = "WTH105" And attribuut.textstring <> "" Then attribuut.textstring = frmGroeptekst.TextBox4  '105 METER
              If attribuut.TagString = "WTH90" And attribuut.textstring <> "" Then attribuut.textstring = frmGroeptekst.TextBox5  '90 METER
              If attribuut.TagString = "WTH75" And attribuut.textstring <> "" Then attribuut.textstring = frmGroeptekst.TextBox6  '75 METER
              If attribuut.TagString = "WTH63" And attribuut.textstring <> "" Then attribuut.textstring = frmGroeptekst.TextBox7  '63 METER
              If attribuut.TagString = "WTH50" And attribuut.textstring <> "" Then attribuut.textstring = frmGroeptekst.TextBox15  '40 METER
              If attribuut.TagString = "WTH40" And attribuut.textstring <> "" Then attribuut.textstring = frmGroeptekst.TextBox16  '50 METER
              If attribuut.TagString = "REGELUNITTYPE" And attribuut.textstring <> "" Then attribuut.textstring = REGELTYPE 'TYPE REGELUNIT
              If attribuut.TagString = "BEVESTIGINGSTYPE" And attribuut.textstring <> "" Then attribuut.textstring = frmGroeptekst.ComboBox1   'BEVESTIGING
              'If attribuut.TagString = "ROLGROTER250" And CheckBox1.Value = True Then attribuut.TextString = frmGroeptekst.TextBox14 & " meter :" 'ROL GROTER DAN 250 METER
              Next k
             bb = ""
             End If
       Next I
       
      End If
      End If
      End If
  Next element2
 End If

Dim ELEMENT7
If frmGroeptekst.OptionButton9.Value = True Then
aantal_groepen = (Val(frmGroeptekst.TextBox4)) + (Val(frmGroeptekst.TextBox5)) + _
(Val(frmGroeptekst.TextBox6)) + (Val(frmGroeptekst.TextBox7)) + (Val(frmGroeptekst.TextBox17))
If (Val(frmGroeptekst.TextBox4)) = 0 Then frmGroeptekst.TextBox4 = "-"
If (Val(frmGroeptekst.TextBox5)) = 0 Then frmGroeptekst.TextBox5 = "-"
If (Val(frmGroeptekst.TextBox6)) = 0 Then frmGroeptekst.TextBox6 = "-"
If (Val(frmGroeptekst.TextBox7)) = 0 Then frmGroeptekst.TextBox7 = "-"
aantal_groepen = aantal_groepen + (Val(frmGroeptekst.TextBox26))
'MsgBox aantal_groepen
If frmGroeptekst.ComboBox3.Enabled = False Then
REGELTYPE = frmGroeptekst.ComboBox2 & " " & aantal_groepen 'ZONDER REGELING
Else
REGELTYPE = frmGroeptekst.ComboBox2 & " " & aantal_groepen & "/" & frmGroeptekst.ComboBox3 'met regeling
End If
If frmGroeptekst.OptionButton7 = True Or frmGroeptekst.OptionButton8 = True Then REGELTYPE = frmGroeptekst.ComboBox2

If frmGroeptekst.ComboBox2 = "RUW-Groot" Or frmGroeptekst.ComboBox2 = "RUW-Klein" Then
REGELTYPE = "RUW" & " " & aantal_groepen
End If
'bloklogo invullen WTH-ZD 16*2,7
  
unittel = frmGroeptekst.TextBox9

If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If



For Each ELEMENT7 In ThisDrawing.ModelSpace
      If ELEMENT7.ObjectName = "AcDbBlockReference" Then
      If UCase(ELEMENT7.Name) = "MAT_SPE_ZD_1627" Then
      Set symbool = ELEMENT7
        If symbool.HasAttributes Then
        attributen = symbool.GetAttributes
        For I = LBound(attributen) To UBound(attributen)
        Set attribuut = attributen(I)
        If attribuut.TagString = "RNU" And attribuut.textstring <> "" Then bb = attribuut.textstring 'REGELUNITNUMMER
            If bb = unitonder10 Then
              For k = LBound(attributen) To UBound(attributen)
              Set attribuut = attributen(k)
              'ELEMENT7.Highlight (True)
              If attribuut.TagString = "WTHZD" And attribuut.textstring <> "" Then attribuut.textstring = "WTH-ZD 16 * 2,7 mm" 'REGELUNITNUMMER
              If attribuut.TagString = "WTH105" And attribuut.textstring <> "" Then attribuut.textstring = frmGroeptekst.TextBox4  '105 METER
              If attribuut.TagString = "WTH90" And attribuut.textstring <> "" Then attribuut.textstring = frmGroeptekst.TextBox5  '90 METER
              If attribuut.TagString = "WTH75" And attribuut.textstring <> "" Then attribuut.textstring = frmGroeptekst.TextBox6  '75 METER
              If attribuut.TagString = "WTH63" And attribuut.textstring <> "" Then attribuut.textstring = frmGroeptekst.TextBox7  '63 METER
              If attribuut.TagString = "REGELUNITTYPE" And attribuut.textstring <> "" Then attribuut.textstring = REGELTYPE 'TYPE REGELUNIT
              If attribuut.TagString = "BEVESTIGINGSTYPE" And attribuut.textstring <> "" Then attribuut.textstring = frmGroeptekst.ComboBox1   'BEVESTIGING
              'If attribuut.TagString = "ROLGROTER250" And CheckBox1.Value = True Then attribuut.TextString = frmGroeptekst.TextBox14 & " meter :" 'ROL GROTER DAN 250 METER
              Next k
             bb = ""
             End If
       Next I
       
      End If
      End If
      End If
  Next ELEMENT7
  
 End If

 For Each element6 In ThisDrawing.ModelSpace
      If element6.ObjectName = "AcDbBlockReference" Then
      If UCase(element6.Name) = "MAT_SPE_FLEX" Or element6.Name = "Mat_spe_FLEX_Aankoppel" Then
      Set symbool = element6
        If symbool.HasAttributes Then
        attributen = symbool.GetAttributes
        For I = LBound(attributen) To UBound(attributen)
        Set attribuut = attributen(I)
        
        If attribuut.TagString = "RNU" And attribuut.textstring <> "" Then bb = attribuut.textstring 'REGELUNITNUMMER
            If bb = unitonder10 Then
              For k = LBound(attributen) To UBound(attributen)
              Set attribuut = attributen(k)
                'element6.Highlight (True)
                'If attribuut.TagString = "RNU" And attribuut.TextString <> "" Then attribuut.TextString = unitonder10 'REGELUNITNUMMER
                If attribuut.TagString = "FLEX_BUIS" And attribuut.textstring <> "" Then attribuut.textstring = "WTH-ZD 16 * 2,7 mm" 'REGELUNITNUMMER
                If attribuut.TagString = "FLEX_METERS" And attribuut.textstring <> "" Then attribuut.textstring = frmGroeptekst.TextBox25  'AANTAL METER
                If attribuut.TagString = "FLEX_MATTEN" And attribuut.textstring <> "" Then attribuut.textstring = frmGroeptekst.TextBox26  'AANTAL METER
                If attribuut.TagString = "REGELUNITTYPE" And attribuut.textstring <> "" Then attribuut.textstring = REGELTYPE  'TYPE REGELUNIT
                If attribuut.TagString = "BEVESTIGINGSTYPE" And attribuut.textstring <> "" Then attribuut.textstring = frmGroeptekst.ComboBox1  'BEVESTIGING
             Next k
             bb = ""
           End If
       
       
       Next I
       
      End If
      End If
      End If
  Next element6

 Update
 
 Dim element3 As Object
If frmGroeptekst.OptionButton2.Value = True Then
aantal_groepen = (Val(frmGroeptekst.TextBox1)) + (Val(frmGroeptekst.TextBox2)) + (Val(frmGroeptekst.TextBox3)) + (Val(frmGroeptekst.TextBox17))
If (Val(frmGroeptekst.TextBox1)) = 0 Then frmGroeptekst.TextBox1 = "-"
If (Val(frmGroeptekst.TextBox2)) = 0 Then frmGroeptekst.TextBox2 = "-"
If (Val(frmGroeptekst.TextBox3)) = 0 Then frmGroeptekst.TextBox3 = "-"
If frmGroeptekst.ComboBox3.Enabled = False Then
REGELTYPE = frmGroeptekst.ComboBox2 & " " & aantal_groepen
Else
REGELTYPE = frmGroeptekst.ComboBox2 & " " & aantal_groepen & "/" & frmGroeptekst.ComboBox3
End If
If frmGroeptekst.OptionButton7 = True Or frmGroeptekst.OptionButton8 = True Then REGELTYPE = frmGroeptekst.ComboBox2

'PE-RT
unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

For Each element3 In ThisDrawing.ModelSpace
      If element3.ObjectName = "AcDbBlockReference" Then
      If UCase(element3.Name) = "MAT_SPE_PE" Or element3.Name = "Mat_spe_PEringleiding" Or element3.Name = "Mat_spe_PE800" Then
      Set symbool = element3
        If symbool.HasAttributes Then
        attributen = symbool.GetAttributes
        For j = LBound(attributen) To UBound(attributen)
        Set attribuut = attributen(j)
          If attribuut.TagString = "RNU" And attribuut.textstring <> "" Then bb = attribuut.textstring 'REGELUNITNUMMER
            If bb = unitonder10 Then
              For k = LBound(attributen) To UBound(attributen)
              Set attribuut = attributen(k)
                'element3.Highlight (True)
                'If attribuut.TagString = "RNU" And attribuut.TextString <> "" Then attribuut.TextString = unitonder10 'REGELUNITNUMMER
                If attribuut.TagString = "PE" And attribuut.textstring <> "" Then attribuut.textstring = frmGroeptekst.ComboBox4 'TYPE BUIS
                If attribuut.TagString = "PE120" And attribuut.textstring <> "" Then attribuut.textstring = frmGroeptekst.TextBox1 '120 METER
                If attribuut.TagString = "PE90" And attribuut.textstring <> "" Then attribuut.textstring = frmGroeptekst.TextBox2  '90 METER
                If attribuut.TagString = "PE60" And attribuut.textstring <> "" Then attribuut.textstring = frmGroeptekst.TextBox3 '60 METER
                If attribuut.TagString = "LMETER" And attribuut.textstring <> "" Then attribuut.textstring = frmGroeptekst.TextBox27 'werkelijke meters totaal
                If attribuut.TagString = "REGELUNITTYPE" And attribuut.textstring <> "" Then attribuut.textstring = REGELTYPE 'TYPE REGELUNIT
                If attribuut.TagString = "BEVESTIGINGSTYPE" And attribuut.textstring <> "" Then attribuut.textstring = frmGroeptekst.ComboBox1  'BEVESTIGING
             Next k
             bb = ""
           End If
       Next j
       
        End If
      End If
      End If
  Next element3
  
 End If
 Update

If frmGroeptekst.OptionButton6 = True Then
aantal_groepen = (Val(frmGroeptekst.TextBox1)) + (Val(frmGroeptekst.TextBox2)) + (Val(frmGroeptekst.TextBox3)) + (Val(frmGroeptekst.TextBox17))
If (Val(frmGroeptekst.TextBox1)) = 0 Then frmGroeptekst.TextBox1 = "-"
If (Val(frmGroeptekst.TextBox2)) = 0 Then frmGroeptekst.TextBox2 = "-"
If (Val(frmGroeptekst.TextBox3)) = 0 Then frmGroeptekst.TextBox3 = "-"
If frmGroeptekst.ComboBox3.Enabled = False Then
REGELTYPE = frmGroeptekst.ComboBox2 & " " & aantal_groepen
Else
REGELTYPE = frmGroeptekst.ComboBox2 & " " & aantal_groepen & "/" & frmGroeptekst.ComboBox3
End If
If frmGroeptekst.OptionButton7 = True Or frmGroeptekst.OptionButton8 = True Then REGELTYPE = frmGroeptekst.ComboBox2

'ALUFLEX
unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If

 Dim element4 As Object
For Each element4 In ThisDrawing.ModelSpace
      If element4.ObjectName = "AcDbBlockReference" Then
      If UCase(element4.Name) = "MAT_SPE_ALU" Or element4.Name = "Mat_spe_ALUringleiding" Then
      Set symbool = element4
        If symbool.HasAttributes Then
        attributen = symbool.GetAttributes
        For j = LBound(attributen) To UBound(attributen)
        Set attribuut = attributen(j)
        If attribuut.TagString = "RNU" And attribuut.textstring <> "" Then bb = attribuut.textstring 'REGELUNITNUMMER
            If bb = unitonder10 Then
              For k = LBound(attributen) To UBound(attributen)
              Set attribuut = attributen(k)
             'element4.Highlight (True)
             'If attribuut.TagString = "RNU" And attribuut.TextString <> "" Then attribuut.TextString = unitonder10 'REGELUNITNUMMER
             If attribuut.TagString = "ALU" And attribuut.textstring <> "" Then attribuut.textstring = frmGroeptekst.ComboBox4 'TYPE BUIS
             If attribuut.TagString = "ALU200" And attribuut.textstring <> "" Then attribuut.textstring = frmGroeptekst.TextBox1  '120 METER
             If attribuut.TagString = "ALU100" And attribuut.textstring <> "" Then attribuut.textstring = frmGroeptekst.TextBox2  '90 METER
             If attribuut.TagString = "ALU50" And attribuut.textstring <> "" Then attribuut.textstring = frmGroeptekst.TextBox3 '60 METER
             If attribuut.TagString = "REGELUNITTYPE" And attribuut.textstring <> "" Then attribuut.textstring = REGELTYPE 'TYPE REGELUNIT
             If attribuut.TagString = "BEVESTIGINGSTYPE" And attribuut.textstring <> "" Then attribuut.textstring = frmGroeptekst.ComboBox1  'BEVESTIGING
             If attribuut.TagString = "PEALU200" And OptionButton6 = True Then attribuut.textstring = "200 meter :" 'Aluflex 200 METER
             If attribuut.TagString = "PEALU100" And OptionButton6 = True Then attribuut.textstring = "100 meter :" 'Aluflex 100 METER
             If attribuut.TagString = "PEALU50" And OptionButton6 = True Then attribuut.textstring = " 50 meter :" 'Aluflex 100 METER
             Next k
             bb = ""
             End If
             
           Next j
       
        End If
      End If
      End If
  Next element4
 End If
  Update
  
  
'  Dim pb2(0 To 2) As Double
'  If OptionButton1.Value = True Then zakken = 210
'  If OptionButton2.Value = True Or OptionButton6.Value = True Then zakken = 179
'  If TextBox11 = "0" And TextBox25 <> "0" Then zakken = 179
'
'  pb2(0) = pb1(0) - (scaal * 460)
'  pb2(1) = pb1(1) + (scaal * zakken) '179) '177'210)
'  pb2(2) = pb1(2)
'
  'juiste regelunitblokje.dwg inserten in de tekening
  Dim bestand2 As String
  bestand2 = frmGroeptekst.ComboBox2 & ".dwg"
  If frmGroeptekst.ComboBox2 = "RUW-Groot" Then bestand2 = "RUW" & ".dwg"
  If frmGroeptekst.ComboBox2 = "RUW-Klein" Then bestand2 = "RUW" & ".dwg"
  If frmGroeptekst.ComboBox2 = "RUB-R" And aantal_groepen > 4 Then bestand2 = "RUH-R" & ".dwg"
  If frmGroeptekst.ComboBox2 = "RUB-RT" And aantal_groepen > 4 Then bestand2 = "RUH-RT" & ".dwg"
  If frmGroeptekst.ComboBox2 = "RUB-S" And aantal_groepen > 4 Then bestand2 = "RUH-S" & ".dwg"
  If frmGroeptekst.ComboBox2 = "VSKO" Then bestand2 = "VSKO-B" & ".dwg"
   Dim bestand3 As String
  bestand3 = "c:\acad2002\dwg\" & frmGroeptekst.ComboBox2 & ".txt"  'tekstbestand met afmetingen
  If frmGroeptekst.ComboBox2 = "VSKO" Then bestand3 = "c:\acad2002\dwg\" & frmGroeptekst.ComboBox2 & "-B.txt"  'tekstbestand met afmetingen
  
  Update
  'MsgBox bestand2 & " - " & bestand3

 Call unitblock(aantal_groepen, bestand2, bestand3, insp, scaal)
  
End Sub
Sub unitblock(aantal_groepen, bestand2, bestand3, insp, scaal)
'unitblok  ----------------
'unitblok  ----------------
'unitblok  ----------------
'unitblok  ----------------
 
 Set blockRefObj = ThisDrawing.ModelSpace.InsertBlock(insp, bestand2, scaal, scaal, 1, 0)
  Update
 
If frmGroeptekst.OptionButton7 = True Or frmGroeptekst.OptionButton8 = True Or frmGroeptekst.ComboBox2 = "RINGLEIDING" Then
 afmunitRING = "RINGLEIDING"
Else


 'open text bestand om afmetingen van de unit uit te lezen
  aantal_groepen2 = aantal_groepen
Const ForReading = 1, ForWriting = 2, ForAppending = 3
Const TristateUseDefault = -2, TristateTrue = -1, TristateFalse = 0
Dim fs, a, afmunit
Set fs = CreateObject("Scripting.FileSystemObject")
Set a = fs.OpenTextFile(bestand3, ForReading, False)
Do While aantal_groepen2 <> 0
    afmunit = a.ReadLine
    aantal_groepen2 = aantal_groepen2 - 1
Loop
a.Close 'sluiten van tekstbestand
End If
 

unittel = frmGroeptekst.TextBox9
If frmGroeptekst.CheckBox3.Value = False Then
  If unittel > 0 And unittel < 10 Then unitonder10 = "0" & frmGroeptekst.TextBox9
End If
If frmGroeptekst.CheckBox3.Value = False Then
  If unittel > 9 Then unitonder10 = frmGroeptekst.TextBox9
End If
If frmGroeptekst.CheckBox3.Value = True Then
   unitonder10 = frmGroeptekst.TextBox9
End If


Dim element5 As Object
unit = frmGroeptekst.ComboBox2
If frmGroeptekst.ComboBox2 = "RUW-Groot" Then unit = "RUW"
If frmGroeptekst.ComboBox2 = "RUW-Klein" Then unit = "RUW"
If frmGroeptekst.ComboBox2 = "RUB-R" And aantal_groepen > 4 Then unit = "RUH-R"
If frmGroeptekst.ComboBox2 = "RUB-RT" And aantal_groepen > 4 Then unit = "RUH-RT"
If frmGroeptekst.ComboBox2 = "RUB-S" And aantal_groepen > 4 Then unit = "RUH-S"
If frmGroeptekst.ComboBox2 = "VSKO" Then unit = "VSKO-B"


For Each element5 In ThisDrawing.ModelSpace
      If element5.ObjectName = "AcDbBlockReference" Then
      If UCase(element5.Name) = unit Then
      Set symbool = element5
        If symbool.HasAttributes Then
        attributen = symbool.GetAttributes
        For I = LBound(attributen) To UBound(attributen)
        Set attribuut = attributen(I)
         If unit = "RINGLEIDING" Then
          If attribuut.TagString = "AFMETINGEN" And attribuut.textstring = "" Then attribuut.textstring = afmunitRING 'AFMETING VAN DEUNIT
          Else
          If attribuut.TagString = "AFMETINGEN" And attribuut.textstring = "" Then attribuut.textstring = afmunit 'AFMETING VAN DEUNIT
        End If
        If attribuut.TagString = "UNITNUMMER" And attribuut.textstring = "" Then attribuut.textstring = unitonder10 'UNITNUMMER
        Next I
       End If
      End If
      End If
 Next element5


  Call RESET
  Unload frmGroeptekst
  'Unload Me
End Sub

Attribute VB_Name = "calc_Waarschuwing"
Sub waarschuwing()
frmCalcWaarschuwing.Show
End Sub

Attribute VB_Name = "frmCalcUnit"
Attribute VB_Base = "0{982FEFB6-90C0-4575-89DC-506AC5262AA2}{FEBEA62F-8196-464A-9290-9DADE78AC8D2}"
Attribute VB_GlobalNameSpace = False
Attribute VB_Creatable = False
Attribute VB_PredeclaredId = True
Attribute VB_Exposed = False
Attribute VB_TemplateDerived = False
Attribute VB_Customizable = False

'G.C.Haak
'kruisje uitschakelen
'BESTANDEN: GROEPTEKSTBLOK.DWG
' "c:\acad2002\dwg\Mat_calculatie.dwg"
' DWG - Herz_calc|Ruh-r_calc|Ruh-N_calc|ruh-rt_calc|rub-r_calc|rub-rt_calc|rubk-r_calc|rubk-rt_calc|LT_calc|lt-s_calc|lt-n_calc
' DWG - RUW_calc|ruv_calc|ruh-s_calc|rub-s_calc|kmv_calc

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If

Call combolijst1 'combobox1 vullen
Call Combolijst2 'combobox2 vullen
Call Combolijst3 'combobox3 vullen
Call combolijst4 'combobox4 vullen
Call combolijst5 'combobox5 vullen
Call combolijst6 'combobox6 vullen
Call leidingtype

ThisDrawing.SendCommand "-layer" & vbCr & "U" & vbCr & "gt" & vbCr & "ON" & vbCr & "gt" & vbCr & "T" & vbCr & "gt" & vbCr & vbCr
Label33 = 0
TextBox9.SetFocus

Dim newLayer As AcadLayer
Set newLayer = ThisDrawing.Layers.Add("GT")
ThisDrawing.ActiveLayer = newLayer

End Sub

Private Sub ComboBox1_Change()
If ComboBox1 = "IFD-Polystyreen" Then ComboBox4 = "PE-RT 14*2 mm"
End Sub
Private Sub ComboBox2_Change()
'type unit
If ComboBox2.Value = "RUH-R" Or ComboBox2.Value = "RUH-RT" Then
  ComboBox3.Enabled = True
  Else
  ComboBox3.Enabled = False
 End If
End Sub
Private Sub CommandButton2_Click()
Unload Me
frmUnitlogo.Show
End Sub


Private Sub commandbutton6_click()
Call Update_calcmodule.update_unitlogo_calc
Unload Me
End Sub
Sub leidingtype()
Dim element As Object
Dim layerObj As AcadLayer

For Each element In ThisDrawing.ModelSpace
      If element.ObjectName = "AcDbBlockReference" Then
      If UCase(element.Name) = "MAT_CALCULATIE" Then
      
      Set symbool = element
        If symbool.HasAttributes Then
        attributen = symbool.GetAttributes
        For I = LBound(attributen) To UBound(attributen)
        Set attribuut = attributen(I)
                
         If attribuut.TagString = "BEVESTIGINGSTYPE" Then ComboBox1 = attribuut.textstring
         If attribuut.TagString = "TB" Then ComboBox4 = attribuut.textstring
         If attribuut.TagString = "AFWERKVLOER" Then ComboBox5 = attribuut.textstring
         If attribuut.TagString = "EXTRA_MATERIALEN" Then ComboBox6 = attribuut.textstring
         
         If attribuut.TagString = "REGELUNITTYPE" Then
          RT = attribuut.textstring
          CONTROLE = InStr(1, RT, "/", vbBinaryCompare)  'staat er een komma in??
            If CONTROLE <> 0 Then
               trimstring = Split(RT, ("/"))
               'MsgBox trimstring(0) & trimstring(1)
               ComboBox2 = trimstring(0)
               ComboBox3 = trimstring(1)
            End If
            If CONTROLE = 0 Then ComboBox2 = RT
         End If
         
       Next I
       
        End If
      End If
      End If
  Next element

End Sub
Private Sub cmdAfsluiten_Click()
Unload Me
End Sub
Private Sub TextBox9_DblClick(ByVal Cancel As MSForms.ReturnBoolean)
TextBox9 = ""
End Sub
Private Sub TextBox10_DblClick(ByVal Cancel As MSForms.ReturnBoolean)
TextBox10 = ""
End Sub
Private Sub TextBox9_Change()
Dim b As Double
On Error Resume Next
TextBox9.SetFocus
b = TextBox9.Text

If Err Then
   TextBox9 = Clear
   CmdBloklogo.Enabled = False
   Exit Sub
  End If
If TextBox9.Text = "" Then CmdBloklogo.Enabled = False
If TextBox9.Text <> "" Then CmdBloklogo.Enabled = True
Label33 = 0

TextBox27 = Clear: TextBox27.Visible = False

End Sub
Private Sub TextBox11_Change()
On Error Resume Next
Dim TA As Double
TA = TextBox11

'----30-6-2004-aangepast omdat ie de rollen niet goed optelde in sommige gevallen
TextBox11 = (Val(TextBox1)) + (Val(TextBox2)) + (Val(TextBox3)) + (Val(TextBox4)) + (Val(TextBox5)) + (Val(TextBox6)) + (Val(TextBox7)) + (Val(TextBox15)) + (Val(TextBox16)) + (Val(TextBox17))
'----30-6-2004-aangepast omdat ie de rollen niet goed optelde in sommige gevallen
Update
If Err Then
   TextBox11 = "0"
  Exit Sub
  End If

If TA > 20 And (frmCalcUnit.OptionButton7 = False And frmCalcUnit.OptionButton8 = False) Then
   'TextBox11.BackColor = &HFFFF&
   MsgBox "PAS OP!!, MEER DAN 20 groepen....!!!!", vbCritical
   TextBox1 = "0": TextBox2 = "0": TextBox3 = "0": TextBox4 = "0"
   TextBox5 = "0": TextBox6 = "0": TextBox7 = "0": TextBox15 = "0": TextBox16 = "0": TextBox11 = "0"
   Call RESET
   'TextBox11.BackColor = &HFFFFFF
   Exit Sub
End If

If Label33 = 0 Then
  If TextBox11 > 15 And ComboBox2 = "KMV" And (frmCalcUnit.OptionButton7 = False And frmCalcUnit.OptionButton8 = False) Then
   MsgBox "PAS OP!!, KMV-verdeler gaat maar tot 15 groepen....!!!!", vbCritical
   Label33 = 1
  End If
End If

If Label33 = 0 Then
  If TextBox11 > 16 And ComboBox2 = "HERZ" And (frmCalcUnit.OptionButton7 = False And frmCalcUnit.OptionButton8 = False) Then
   MsgBox "PAS OP!!, HERZ-verdeler gaat maar tot 16 groepen....!!!!", vbCritical
   Label33 = 1
  End If
End If

If TextBox11 <> "0" Then TextBox17.Enabled = True


End Sub
Private Sub TextBox12_Change()
Dim C As Double
On Error Resume Next

C = TextBox12.Text

If Err Then
   TextBox12 = Clear
   Exit Sub
  End If
End Sub
Sub combolijst1()
ComboBox1.AddItem "Vlechtdraad"
ComboBox1.AddItem "Witmarmerbeugels"
ComboBox1.AddItem "Beugels/Nagels"
ComboBox1.AddItem "Eigen middelen"
ComboBox1.AddItem "IFD-Polystyreen"
ComboBox1.AddItem "Isoclips"
ComboBox1.AddItem "Keg"
ComboBox1.AddItem "Montagestrip"
ComboBox1.AddItem "Noppenplaat"
ComboBox1.AddItem "Schietbeugels"
ComboBox1.AddItem "Ty-raps"
ComboBox1.AddItem "Varisoclips"
ComboBox1.ListIndex = 1

End Sub
Sub Combolijst2()
ComboBox2.AddItem "HERZ"
ComboBox2.AddItem "KMV"
ComboBox2.AddItem "LT"
ComboBox2.AddItem "LT-N"
ComboBox2.AddItem "LTS" 'aangepast
ComboBox2.AddItem "LTS-N" 'aangepast
ComboBox2.AddItem "LT-VK" 'aangepast
ComboBox2.AddItem "RUB-R"
ComboBox2.AddItem "RUB-RT"
ComboBox2.AddItem "RUBK-R"
ComboBox2.AddItem "RUBK-RT"
ComboBox2.AddItem "RUB-S"
ComboBox2.AddItem "RU-EE"
ComboBox2.AddItem "RUH-N"
ComboBox2.AddItem "RUH-R"
ComboBox2.AddItem "RUH-RT"
ComboBox2.AddItem "RUH-S"
ComboBox2.AddItem "RUV"
ComboBox2.AddItem "RU-WK"
ComboBox2.AddItem "RU-WKN" 'aangepast
ComboBox2.AddItem "RU-WKS" 'aangepast
ComboBox2.AddItem "RU-WW"
ComboBox2.AddItem "RU-WWN" 'aangepast
ComboBox2.AddItem "RU-WWS" 'aangepast
'ComboBox2.AddItem "VSKO"
ComboBox2.ListIndex = 15
ComboBox2.MatchEntry = fmMatchEntryFirstLetter
End Sub
Sub Combolijst3()
ComboBox3.AddItem "KT220"
ComboBox3.AddItem "KT24"
ComboBox3.AddItem "TH7420"
ComboBox3.ListIndex = 2
ComboBox3.MatchEntry = fmMatchEntryFirstLetter
End Sub
Sub combolijst4()
 ComboBox4.AddItem "ALUFLEX 14*2 mm"
 ComboBox4.AddItem "ALUFLEX 16*2 mm"
 ComboBox4.AddItem "ALUFLEX 18*2 mm"
 ComboBox4.AddItem "ALUFLEX 20*2 mm"
 ComboBox4.AddItem "PE-RT 10*1,25 mm"
 ComboBox4.AddItem "PE-RT 14*2 mm"
 ComboBox4.AddItem "PE-RT 16*2 mm"
 ComboBox4.AddItem "WTH-ZD 16*2,7 mm"
 ComboBox4.AddItem "WTH-ZD 20*3,4 mm"
 ComboBox4.ListIndex = 8
End Sub
Sub combolijst5()
 ComboBox5.AddItem "Zand-cement"
 ComboBox5.AddItem "Gietvloer"
 ComboBox5.AddItem "Monolitisch"
 ComboBox5.AddItem "Constructievloer"
 ComboBox5.ListIndex = 0
End Sub
Sub combolijst6()
 ComboBox6.AddItem "Geen"
 ComboBox6.AddItem "Bevestigingsnetten"
 ComboBox6.AddItem "Krimpnetten"
 ComboBox6.AddItem "Variso isolatie 20mm thermisch"
 ComboBox6.AddItem "Variso isolatie 20mm akoestisch"
 ComboBox6.AddItem "Variso isolatie 30mm thermisch"
 ComboBox6.AddItem "Variso isolatie 30mm akoestisch"
 ComboBox6.AddItem "Polystyreen isolatie"
 ComboBox6.AddItem "Folie"
 ComboBox6.AddItem "Noppenplaat"
 ComboBox6.ListIndex = 0
End Sub
Private Sub CmdBloklogo_Click()
On Error Resume Next
If ComboBox2 = "" Then
    MsgBox "Je bent 'Type unit' vergeten in te vullen..!!"
    ComboBox2.SetFocus
    Exit Sub
    End If
If ComboBox1 = "" Then
    MsgBox "Je bent 'Bevestigingsmateriaal' vergeten in te vullen..!!"
    ComboBox1.SetFocus
    Exit Sub
    End If
If ComboBox4 = "" Then
    MsgBox "Je bent 'Type buis' vergeten in te vullen..!!"
    ComboBox4.SetFocus
    Exit Sub
    End If

frmCalcUnit.Hide
TextBox9.Locked = False
    Set newLayer = ThisDrawing.Layers.Add("BLOKLOGO")
    ThisDrawing.ActiveLayer = newLayer
    Update
    ThisDrawing.SendCommand "-layer" & vbCr & "U" & vbCr & "*" & vbCr & vbCr
    Update
Call Schaal(scaal)

 bestand = "c:\acad2002\dwg\Mat_calculatie.dwg"



If frmCalcUnit.TextBox29 <> "" Then scaal = frmCalcUnit.TextBox29
Dim pb1 As Variant
pb1 = ThisDrawing.Utility.GetPoint(, "Plaats startpunt....")
Set blockRefObj = ThisDrawing.ModelSpace.InsertBlock(pb1, bestand, scaal, scaal, 1, 0)
''''If TextBox11 <> "0" And TextBox25 <> "0" Then Set blockRefObj = ThisDrawing.ModelSpace.InsertBlock(pb1, bestand20, scaal, scaal, 1, 0)
Update
If Err Then
    frmCalcUnit.Show
    Exit Sub
    End If

Dim element2 As Object

If ComboBox3.Enabled = False Then
REGELTYPE = ComboBox2 'ZONDER REGELING
Else
REGELTYPE = ComboBox2 & " / " & ComboBox3  'met regeling
End If
''If frmCalcUnit.OptionButton7 = True Or frmCalcUnit.OptionButton8 = True Then REGELTYPE = ComboBox2

unittel = frmCalcUnit.TextBox9

If unittel > 0 And unittel < 10 Then unitonder10 = "0" & frmCalcUnit.TextBox9
If unittel > 9 Then unitonder10 = frmCalcUnit.TextBox9


For Each element2 In ThisDrawing.ModelSpace
      If element2.ObjectName = "AcDbBlockReference" Then
      If UCase(element2.Name) = "MAT_CALCULATIE" Then
      Set symbool = element2
        If symbool.HasAttributes Then
        attributen = symbool.GetAttributes
        For I = LBound(attributen) To UBound(attributen)
        Set attribuut = attributen(I)
        If attribuut.TagString = "RNU" And attribuut.textstring = "" Then attribuut.textstring = unitonder10 'REGELUNITNUMMER
        If attribuut.TagString = "REGELUNITTYPE" And attribuut.textstring = "" Then attribuut.textstring = REGELTYPE  'TYPE REGELUNIT
        If attribuut.TagString = "BEVESTIGINGSTYPE" And attribuut.textstring = "" Then attribuut.textstring = ComboBox1  'BEVESTIGING
        If attribuut.TagString = "TB" And attribuut.textstring = "" Then attribuut.textstring = ComboBox4 'TYPE BUIS
        If attribuut.TagString = "AFWERKVLOER" And attribuut.textstring = "" Then attribuut.textstring = ComboBox5 'AFWERKVLOER
        If attribuut.TagString = "EXTRA_MATERIALEN" And attribuut.textstring = "" Then attribuut.textstring = ComboBox6 'EXTRA MATERIALEN
        Next I
       
      End If
      End If
      End If
  Next element2
 
 Update
 
   
  Dim pb2(0 To 2) As Double
 
  pb2(0) = pb1(0) - (scaal * 460)
  pb2(1) = pb1(1) + (scaal * 225) '177'210)
  pb2(2) = pb1(2)
  
  'juiste regelunitblokje.dwg inserten in de tekening
  bestand2 = ComboBox2 & "_calc.dwg"
  
  If ComboBox2 = "RUB-R" Or ComboBox2 = "RUB-RT" Then
     Call calc_Waarschuwing.waarschuwing
     If frmCalcUnit.TextBox30 = "2" Then bestand2 = "RUH-R" & "_calc.dwg"
  End If
  
 
  Call Calc_Unitblok.Unitblok(scaal, pb2, bestand2)
  Unload Me

End Sub
Sub MESSAGE(XWAARDE)

End Sub
Sub Schaal(scaal)
frmCalcUnit.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
Update
End Sub

Attribute VB_Name = "frmCalcWaarschuwing"
Attribute VB_Base = "0{4DEEB656-91A7-4504-8D16-47DE4D238A09}{17D9003B-C7A5-4DC6-8174-7C172D3FCBCC}"
Attribute VB_GlobalNameSpace = False
Attribute VB_Creatable = False
Attribute VB_PredeclaredId = True
Attribute VB_Exposed = False
Attribute VB_TemplateDerived = False
Attribute VB_Customizable = False

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000


Private Sub cmdnietsveranderen_Click()
If OptionButton1.Value = True Then frmCalcUnit.TextBox30 = 1  ' < 5 groepen
If OptionButton2.Value = True Then frmCalcUnit.TextBox30 = 2  ' > 4 groepen
Unload Me
End Sub

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If

End Sub
Private Sub OptionButton1_Click()
If OptionButton1.Value = True Then cmdnietsveranderen.Enabled = True
End Sub
Private Sub OptionButton2_Click()
If OptionButton2.Value = True Then cmdnietsveranderen.Enabled = True
End Sub

Attribute VB_Name = "frmCalculatieKaderlogo"
Attribute VB_Base = "0{549A6084-2FA1-47C4-B1E1-10EA17D8C6B6}{F2A91FCB-4E02-4CCB-A3B4-A1D5C0672583}"
Attribute VB_GlobalNameSpace = False
Attribute VB_Creatable = False
Attribute VB_PredeclaredId = True
Attribute VB_Exposed = False
Attribute VB_TemplateDerived = False
Attribute VB_Customizable = False

'29-09-2003 Plaatsen van Kaderlogo
'M.Bosch en G.C.Haak
'kruisje uitschakelen
'kaderlogocalc.dwg
#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
Dim blockObj As AcadBlock
Call Calc_Check_Kaderlogo.Check_kaderlogocalc
 
TextBox3.SetFocus
Call combolijst1
Call Combolijst2
Call Schaal(scaal)
If scaal = 2 Then
schaalv = "1:100"
Else
schaalv = "1:50"
End If
If scaal = 4 Then schaalv = "1:200"


Call loginnaam(lognaam) 'Loginnaam oproepen
Call datum(kdate)


Dim element As Object
For Each element In ThisDrawing.ModelSpace
      If element.ObjectName = "AcDbBlockReference" Then
      If UCase(element.Name) = "KADERLOGOCALC" Then
      Set symbool = element
        If symbool.HasAttributes Then
        attributen = symbool.GetAttributes
        For I = LBound(attributen) To UBound(attributen)
        Set attribuut = attributen(I)
        If attribuut.TagString = "PROJECTNAAM" Then TextBox3 = attribuut.textstring
        If attribuut.TagString = "MONTAGEADRES" Then TextBox4 = attribuut.textstring
        If attribuut.TagString = "MONTAGEPLAATS" Then TextBox5 = attribuut.textstring
        If attribuut.TagString = "PROJECTNUMMER" Then TextBox6 = Left(ThisDrawing.GetVariable("dwgname"), 9) 'attribuut.TextString
        If attribuut.TagString = "BLAD" Then ComboBox1 = attribuut.textstring
        If attribuut.TagString = "BLAD" And attribuut.textstring = "" Then ComboBox1 = "1"
        If attribuut.TagString = "FORMAAT" Then TextBox8 = attribuut.textstring
        If attribuut.TagString = "TEKENAAR" And attribuut.textstring = "" Then TextBox9 = lognaam
        If attribuut.TagString = "TEKENAAR" And attribuut.textstring <> "" Then TextBox9 = attribuut.textstring
        If attribuut.TagString = "SCHAAL" And attribuut.textstring = "" Then TextBox10 = schaalv
        If attribuut.TagString = "SCHAAL" And attribuut.textstring <> "" Then TextBox10 = attribuut.textstring
        If attribuut.TagString = "DATUM" And attribuut.textstring = "" Then TextBox11 = kdate ' & "|" & lognaam
        If attribuut.TagString = "DATUM" And attribuut.textstring <> "" Then TextBox11 = attribuut.textstring
        If attribuut.TagString = "WIJZIGING1" And attribuut.textstring <> "" Then TextBox12 = attribuut.textstring
        If attribuut.TagString = "WIJZIGING2" And attribuut.textstring <> "" Then TextBox13 = attribuut.textstring
        If attribuut.TagString = "WIJZIGING3" And attribuut.textstring <> "" Then TextBox14 = attribuut.textstring
        If attribuut.TagString = "WIJZIGING4" And attribuut.textstring <> "" Then TextBox15 = attribuut.textstring
        Next I
       End If
     End If
   End If
  Next element
  
Dim element10 As Object
For Each element10 In ThisDrawing.ModelSpace
      If element10.ObjectName = "AcDbBlockReference" Then
      If UCase(element10.Name) = "VLRWTH" Then
      Set symbool = element10
        If symbool.HasAttributes Then
        attributen = symbool.GetAttributes
        For j = LBound(attributen) To UBound(attributen)
        Set attribuut = attributen(j)
        If attribuut.TagString = "TEKENINGNUMMER" Then TextBox21 = attribuut.textstring
        If attribuut.TagString = "BLAD_BWK" Then TextBox22 = attribuut.textstring
        If attribuut.TagString = "DATUM_BWK" Then TextBox23 = attribuut.textstring
        If attribuut.TagString = "PROJEKTLEIDER" Then ComboBox2 = attribuut.textstring
        If attribuut.TagString = "PROJEKTLEIDER" And attribuut.textstring = "" Then ComboBox2 = "F.v/d Corput"
        Next j
       End If
     End If
   End If
  Next element10

If TextBox6.Value <> "" Then TextBox6.Locked = True
If TextBox8.Value <> "" Then TextBox8.Locked = True
If TextBox10.Value <> "" Then TextBox10.Locked = True
Update
End Sub
Sub datum(kdate)
datumacad1 = ThisDrawing.GetVariable("cdate")
datumacad = Left(datumacad1, 8)
dag = Right(datumacad, 2)
maand = Left(datumacad, 6)
maand2 = Right(maand, 2)
jaar = Left(datumacad, 4)

kdate = dag & "-" & maand2 & "-" & jaar

End Sub
Private Sub CheckBox2_Click()
Call loginnaam(lognaam)
Call datum(kdate)
If CheckBox2.Value = True Then
TextBox12 = kdate & "|" & lognaam
Else
TextBox12 = ""
End If
End Sub

Private Sub CheckBox3_Click()
Call loginnaam(lognaam)
Call datum(kdate)
If CheckBox3.Value = True Then
TextBox13 = kdate & "|" & lognaam
Else
TextBox13 = ""
End If
End Sub

Private Sub CheckBox4_Click()
Call loginnaam(lognaam)
Call datum(kdate)
If CheckBox4.Value = True Then
TextBox14 = kdate & "|" & lognaam
Else
TextBox14 = ""
End If
End Sub
Private Sub CheckBox5_Click()
Call loginnaam(lognaam)
Call datum(kdate)
If CheckBox5.Value = True Then
TextBox15 = kdate & "|" & lognaam
Else
TextBox15 = ""
End If
End Sub
Private Sub CheckBox1_Click()
Call loginnaam(lognaam)
Call datum(kdate)
If CheckBox1.Value = True Then
TextBox19 = kdate & "|" & lognaam
Else
TextBox19 = ""
End If
End Sub
Private Sub TextBox10_Change()
If TextBox10.Value <> "" Then TextBox10.Locked = True
End Sub
Private Sub TextBox3_DblClick(ByVal Cancel As MSForms.ReturnBoolean)
TextBox3 = ""
End Sub
Private Sub TextBox4_DblClick(ByVal Cancel As MSForms.ReturnBoolean)
TextBox4 = ""
End Sub
Private Sub TextBox5_DblClick(ByVal Cancel As MSForms.ReturnBoolean)
TextBox5 = ""
End Sub
Private Sub CmdUpdate_Click()
Grootklein = Left(ThisDrawing.GetVariable("dwgname"), 2) 'nummer checken
scaal = frmCalculatieKaderlogo.TextBox20

   For Each element10 In ThisDrawing.ModelSpace
      If element10.ObjectName = "AcDbBlockReference" Then
      If UCase(element10.Name) = "KADERLOGOCALC" Then
      Set symbool = element10
        If symbool.HasAttributes Then
        attributen = symbool.GetAttributes
        For I = LBound(attributen) To UBound(attributen)
        Set attribuut = attributen(I)
        If attribuut.TagString = "PROJECTNAAM" Then attribuut.textstring = TextBox3
        If attribuut.TagString = "MONTAGEADRES" Then attribuut.textstring = TextBox4
        If attribuut.TagString = "MONTAGEPLAATS" Then attribuut.textstring = TextBox5
        If attribuut.TagString = "PROJECTNUMMER" And Grootklein = "p0" Then attribuut.textstring = LCase(TextBox6)
        If attribuut.TagString = "PROJECTNUMMER" And Grootklein <> "p0" Then attribuut.textstring = UCase(TextBox6)
        If attribuut.TagString = "BLAD" Then attribuut.textstring = ComboBox1
        If attribuut.TagString = "FORMAAT" Then attribuut.textstring = TextBox8
        If attribuut.TagString = "TEKENAAR" Then attribuut.textstring = TextBox9
        If attribuut.TagString = "SCHAAL" Then attribuut.textstring = TextBox10
        If attribuut.TagString = "DATUM" Then attribuut.textstring = TextBox11
        If attribuut.TagString = "WIJZIGING1" Then attribuut.textstring = TextBox12
        If attribuut.TagString = "WIJZIGING2" Then attribuut.textstring = TextBox13
        If attribuut.TagString = "WIJZIGING3" Then attribuut.textstring = TextBox14
        If attribuut.TagString = "WIJZIGING4" Then attribuut.textstring = TextBox15
     Next I

      End If
      End If
      End If
      Next element10
Update
Call BLOK2
End Sub
Private Sub BLOK2()
    For Each element11 In ThisDrawing.ModelSpace
      If element11.ObjectName = "AcDbBlockReference" Then
      If UCase(element11.Name) = "VLRWTH" Then
      Set symbool = element11
        If symbool.HasAttributes Then
        attributen = symbool.GetAttributes
       For k = LBound(attributen) To UBound(attributen)
        Set attribuut = attributen(k)
        If attribuut.TagString = "TEKENINGNUMMER" Then attribuut.textstring = TextBox21
        If attribuut.TagString = "BLAD_BWK" Then attribuut.textstring = TextBox22
        If attribuut.TagString = "DATUM_BWK" Then attribuut.textstring = TextBox23
        If attribuut.TagString = "PROJEKTLEIDER" Then attribuut.textstring = ComboBox2
       Next k

      End If
      End If
      End If
     Next element11
Update
Call cmdAfsluiten_Click
End Sub
Private Sub cmdAfsluiten_Click()
Unload Me
End Sub
Sub Schaal(scaal)
frmCalculatieKaderlogo.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
TextBox20 = scaal
Update
End Sub
Sub loginnaam(lognaam)
lognaam = ThisDrawing.GetVariable("loginname")
lognaam = UCase(lognaam)
If lognaam = "CBOOI" Then lognaam = "CB"
If lognaam = "DVERB" Then lognaam = "DV"
If lognaam = "EHOUW" Then lognaam = "EH"
If lognaam = "GWIJK" Then lognaam = "GW"
If lognaam = "LARS" Then lognaam = "LvD"
If lognaam = "JZILV" Then lognaam = "JZ"
If lognaam = "KREITERJ" Then lognaam = "JK"
If lognaam = "LIESBETH" Then lognaam = "LR"
If lognaam = "RRAAT" Then lognaam = "RR"
If lognaam = "JHAM" Then lognaam = "JH"
If lognaam = "GERARD" Then lognaam = "GCH"
End Sub
Sub combolijst1()

ComboBox1.AddItem "1"
ComboBox1.AddItem "W00"
ComboBox1.AddItem "W01"
ComboBox1.AddItem "W02"
ComboBox1.AddItem "W03"
ComboBox1.AddItem "W04"
ComboBox1.AddItem "W05"
ComboBox1.AddItem "W06"
ComboBox1.AddItem "W07"
ComboBox1.AddItem "W08"
ComboBox1.ListIndex = 0
ComboBox1.MatchEntry = fmMatchEntryFirstLetter
End Sub

Sub Combolijst2()

ComboBox2.AddItem "A. Schenkel"
ComboBox2.AddItem "D. Heron"
ComboBox2.AddItem "F. v/d Corput"
ComboBox2.AddItem "F. Prenen"
ComboBox2.ListIndex = 2
ComboBox2.MatchEntry = fmMatchEntryFirstLetter
End Sub

''''''''Private Sub CommandButton1_Click()
'''''''''TextBox3 = StrConv(TextBox3, vbProperCase)
'''''''''TextBox4 = StrConv(TextBox4, vbProperCase)
'''''''''TextBox5 = StrConv(TextBox5, vbProperCase)
''''''''
''''''''Grootklein = Left(ThisDrawing.GetVariable("dwgname"), 2) 'nummer checken
''''''''
''''''''Dim element10 As Object
''''''''If CheckBox9.Value = False Then
''''''''     For Each element10 In ThisDrawing.ModelSpace
''''''''      If element10.ObjectName = "AcDbBlockReference" Then
''''''''      If element10.Name = "Kaderlogo" And CheckBox9.Value = False Then
''''''''      Set symbool = element10
''''''''        If symbool.HasAttributes Then
''''''''        attributen = symbool.GetAttributes
''''''''        For I = LBound(attributen) To UBound(attributen)
''''''''        Set attribuut = attributen(I)
''''''''        If attribuut.TagString = "OPDRACHTGEVER" Then attribuut.textstring = TextBox1
''''''''        If attribuut.TagString = "PLAATS" Then attribuut.textstring = UCase(TextBox2)
''''''''        If attribuut.TagString = "PROJECTNAAM" Then attribuut.textstring = TextBox3
''''''''        If attribuut.TagString = "MONTAGEADRES" Then attribuut.textstring = TextBox4
''''''''        If attribuut.TagString = "MONTAGEPLAATS" Then attribuut.textstring = TextBox5
''''''''        If attribuut.TagString = "PROJECTNUMMER" And Grootklein = "p0" Then attribuut.textstring = LCase(TextBox6)
''''''''        If attribuut.TagString = "PROJECTNUMMER" And Grootklein <> "p0" Then attribuut.textstring = UCase(TextBox6)
''''''''        If attribuut.TagString = "BLAD" Then attribuut.textstring = ComboBox1
''''''''        If attribuut.TagString = "FORMAAT" Then attribuut.textstring = TextBox8
''''''''        If attribuut.TagString = "TEKENAAR" Then attribuut.textstring = TextBox9
''''''''        If attribuut.TagString = "SCHAAL" Then attribuut.textstring = TextBox10
''''''''        If attribuut.TagString = "DATUM" Then attribuut.textstring = TextBox11
''''''''        If attribuut.TagString = "WIJZIGING1" Then attribuut.textstring = TextBox12
''''''''        If attribuut.TagString = "WIJZIGING2" Then attribuut.textstring = TextBox13
''''''''        If attribuut.TagString = "WIJZIGING3" Then attribuut.textstring = TextBox14
''''''''        If attribuut.TagString = "WIJZIGING4" Then attribuut.textstring = TextBox15
''''''''        If attribuut.TagString = "WIJZIGING5" Then attribuut.textstring = TextBox16
''''''''        If attribuut.TagString = "WIJZIGING6" Then attribuut.textstring = TextBox17
''''''''        If attribuut.TagString = "WIJZIGING7" Then attribuut.textstring = TextBox18
''''''''        If attribuut.TagString = "REVISIE" Then attribuut.textstring = TextBox19
''''''''       Next I
''''''''
''''''''      End If
''''''''      End If
''''''''      End If
''''''''      Next element10
''''''''End If
'''''''''Else
''''''''
''''''''
'''''''' ' For Each GG In ThisDrawing.ModelSpace
'''''''' '   If GG.ObjectName = "AcDbBlockReference" Then
'''''''' '      If GG.Name = "Kaderlogo" Then
'''''''' '         a = GG.InsertionPoint
'''''''' '         'GG.Delete
''''''''          'Set blockRefObj = ThisDrawing.ModelSpace.InsertBlock(a, "C:\ACAD2002\DWG\bl-bouw.dwg", 1, 1, 1, 0)
'''''''' '       End If
'''''''' '   End If
'''''''' ' Next
''''''''
''''''''
''''''''If CheckBox9 = True And CheckBox10 = False Then
''''''''Dim element As Object
''''''''Dim layerObj As AcadLayer
'''''''''Kaderlogo verwijderen
''''''''     For Each element In ThisDrawing.ModelSpace
''''''''      If element.ObjectName = "AcDbBlockReference" Then
''''''''         If element.Name = "Kaderlogo" Then
''''''''          engkaderlogo = element.InsertionPoint
''''''''          element.Erase
''''''''         End If
''''''''      Update
''''''''      End If
''''''''     Next element
''''''''
''''''''
''''''''         On Error Resume Next
''''''''         For Each element In ThisDrawing.ModelSpace
''''''''         If element.ObjectName = "AcDbBlockReference" Then
''''''''         If element.Name <> "KaderlogoEngels" Then
''''''''
''''''''
''''''''    If Err Then
''''''''    CheckBox10.Value = False
''''''''    frmCalculatieKaderlogo.Show
''''''''    Exit Sub
''''''''    End If
''''''''
''''''''         Dim bestand91 As String
''''''''         bestand91 = "C:\ACAD2002\DWG\KaderlogoEngels.dwg"
''''''''         Set blockRefObj = ThisDrawing.ModelSpace.InsertBlock(engkaderlogo, bestand91, 1, 1, 1, 0)
''''''''         End If
''''''''         End If
''''''''         Next element
''''''''         Update
''''''''         CheckBox10 = True
''''''''End If
''''''''
''''''''
''''''''
''''''''Dim element11 As Object
''''''''For Each element11 In ThisDrawing.ModelSpace
''''''''     If element11.ObjectName = "AcDbBlockReference" Then
''''''''      If element11.Name = "KaderlogoEngels" And CheckBox9.Value = True Then
''''''''      Set symbool = element11
''''''''        If symbool.HasAttributes Then
''''''''        attributen = symbool.GetAttributes
''''''''        For I = LBound(attributen) To UBound(attributen)
''''''''        Set attribuut = attributen(I)
''''''''        If attribuut.TagString = "OPDRACHTGEVER" Then attribuut.textstring = TextBox1
''''''''        If attribuut.TagString = "PLAATS" Then attribuut.textstring = UCase(TextBox2)
''''''''        If attribuut.TagString = "PROJECTNAAM" Then attribuut.textstring = TextBox3
''''''''        If attribuut.TagString = "MONTAGEADRES" Then attribuut.textstring = TextBox4
''''''''        If attribuut.TagString = "MONTAGEPLAATS" Then attribuut.textstring = TextBox5
''''''''        If attribuut.TagString = "PROJECTNUMMER" And Grootklein = "p0" Then attribuut.textstring = LCase(TextBox6)
''''''''        If attribuut.TagString = "PROJECTNUMMER" And Grootklein <> "p0" Then attribuut.textstring = UCase(TextBox6)
''''''''        If attribuut.TagString = "BLAD" Then attribuut.textstring = ComboBox1
''''''''        If attribuut.TagString = "FORMAAT" Then attribuut.textstring = TextBox8
''''''''        If attribuut.TagString = "TEKENAAR" Then attribuut.textstring = TextBox9
''''''''        If attribuut.TagString = "SCHAAL" Then attribuut.textstring = TextBox10
''''''''        If attribuut.TagString = "DATUM" Then attribuut.textstring = TextBox11
''''''''        If attribuut.TagString = "WIJZIGING1" Then attribuut.textstring = TextBox12
''''''''        If attribuut.TagString = "WIJZIGING2" Then attribuut.textstring = TextBox13
''''''''        If attribuut.TagString = "WIJZIGING3" Then attribuut.textstring = TextBox14
''''''''        If attribuut.TagString = "WIJZIGING4" Then attribuut.textstring = TextBox15
''''''''        If attribuut.TagString = "WIJZIGING5" Then attribuut.textstring = TextBox16
''''''''        If attribuut.TagString = "WIJZIGING6" Then attribuut.textstring = TextBox17
''''''''        If attribuut.TagString = "WIJZIGING7" Then attribuut.textstring = TextBox18
''''''''        If attribuut.TagString = "REVISIE" Then attribuut.textstring = TextBox19
''''''''
''''''''       Next I
''''''''
''''''''
''''''''
''''''''        End If
''''''''      End If
''''''''    End If
''''''''Next element11
'''''''''End If
'''''''''End If 'checkbox9
''''''''Update
''''''''
''''''''
''''''''End Sub
