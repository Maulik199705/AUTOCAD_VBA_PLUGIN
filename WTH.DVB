Attribute VB_Name = "F_About"
Attribute VB_Base = "0{2FB477EB-071A-4DE1-B77C-48BD9DF66365}{7848DC04-3059-4F55-B748-880F0DCA07B4}"
Attribute VB_GlobalNameSpace = False
Attribute VB_Creatable = False
Attribute VB_PredeclaredId = True
Attribute VB_Exposed = False
Attribute VB_TemplateDerived = False
Attribute VB_Customizable = False

Private Sub CommandButton1_Click()
    Unload Me
End Sub

Private Sub UserForm_Initialize()
    ListBox1.Clear
    ListBox1.AddItem ""
    ListBox1.AddItem "Leidingtekenprogramma WTH"
    ListBox1.AddItem ""
    ListBox1.AddItem "Door E.Breedveld"
    ListBox1.AddItem ""
    ListBox1.AddItem "CAD E&D Education Developing"
    ListBox1.AddItem "www.caded.nl"
    ListBox1.AddItem "tel: 078-6911342"
    ListBox1.AddItem "mob: 06-28817856"
    ListBox1.AddItem ""
    ListBox1.AddItem ""
    ListBox1.AddItem "Versie 1.0    1 april 2003"
    ListBox1.AddItem "Versie 1.1    21 mei 2003 (finetunen gehele programma)"
    ListBox1.AddItem "Versie 1.2    27 mei 2003 (maken aanpassingen nav bezoek 26 mei)"
    ListBox1.AddItem "Versie 1.3    31 juli 2003 (maken aanpassingen/ uitbreiding slingerafronding nav bezoek 11 juli)"
    ListBox1.AddItem "Versie 1.4    31 jan 2004 (finetunen voor produktie)"
    ListBox1.AddItem "Versie 1.5    10 feb 2004 (aanpassen offset duo-leiding)"
    ListBox1.AddItem "Versie 1.6    14 feb 2004 (aanpassen offset duo-leiding)"
    ListBox1.AddItem "Versie 2.0    27 mei Finetuning en toevoeging lengtemonitor"
    ListBox1.AddItem "Versie 2.1    14 juni Finetuning n.a.v. demo aan gebruikers 27 mei 2004"
    
End Sub

Attribute VB_Name = "F_FiltetOLD"
Attribute VB_Base = "0{39F1C68E-6241-45E8-81C7-242BF724BE20}{96D06B24-643E-471D-87D3-1FFC52EEC757}"
Attribute VB_GlobalNameSpace = False
Attribute VB_Creatable = False
Attribute VB_PredeclaredId = True
Attribute VB_Exposed = False
Attribute VB_TemplateDerived = False
Attribute VB_Customizable = False






Private Sub CommandButton3_Click()
    Dim LijnObj1 As AcadLine
    Dim LijnObj2 As AcadLine
    
    Dim Psnij As Variant
    
    Set LijnObj1 = ThisDrawing.ModelSpace.Item(ThisDrawing.ModelSpace.Count - 1)
    Set LijnObj2 = ThisDrawing.ModelSpace.Item(ThisDrawing.ModelSpace.Count - 2)
    
    Psnij = LijnObj1.IntersectWith(LijnObj2, acExtendNone)
    MsgBox Psnij(0) & Chr(10) & Chr(13) & Psnij(1)

    Dim HoekVerchil As Double
    MsgBox "Hoek1=" & ThisDrawing.Utility.AngleToString(LijnObj1.Angle, acDegrees, 6) '= hoek in graden
    MsgBox "Hoek1=" & ThisDrawing.Utility.AngleToString(LijnObj2.Angle, acDegrees, 6) '= hoek in graden
    HoekVerchil = (LijnObj2.Angle - LijnObj1.Angle) / 2
    
    'MsgBox "Hoek=" & Hoek
    MsgBox "Hoekverschil" & ThisDrawing.Utility.AngleToString(HoekVerchil, acDegrees, 6) '= hoek in graden
    
    'If HoekVerchil < 0 Then HoekVerchil = HoekVerchil + 3.1415
    
'    Dim HoekInGraden As Double
'    HoekInGraden = ThisDrawing.Utility.AngleToString(6.283, acDegrees, 6)  '= hoek in graden
'    MsgBox HoekInGraden
    
    Dim Aanliggende As Double
    Dim SchuineZijde As Double
    Dim Radius As Double
    
    Radius = 10
    Aanliggende = Radius / Tan(HoekVerchil)
    MsgBox "Aanliggende = " & Aanliggende
    
    SchuineZijde = Radius / Sin(HoekVerchil)
    MsgBox "SchuineZijde = " & SchuineZijde
    
    Dim CenterPunt As Variant
    Dim HOEK As Variant
    HOEK = (LijnObj2.Angle + LijnObj1.Angle) / 2
    MsgBox "Hoek=" & ThisDrawing.Utility.AngleToString(HOEK, acDegrees, 6) '= hoek in graden
    CenterPunt = ThisDrawing.Utility.PolarPoint(Psnij, HOEK, SchuineZijde)
    MsgBox "x=" & CenterPunt(0) & Chr(10) & Chr(13) & "y=" & CenterPunt(1)
    
    
    Dim CirkelObj As AcadCircle
    Set CirkelObj = ThisDrawing.ModelSpace.AddCircle(CenterPunt, Radius)
    CirkelObj.Update
    
    
    
End Sub

Attribute VB_Name = "F_InvoerRollengte"
Attribute VB_Base = "0{85EC52B6-62D1-4A54-A158-BC3F821C88B1}{0872433B-1F2C-42DB-9125-E011AF5151C8}"
Attribute VB_GlobalNameSpace = False
Attribute VB_Creatable = False
Attribute VB_PredeclaredId = True
Attribute VB_Exposed = False
Attribute VB_TemplateDerived = False
Attribute VB_Customizable = False

Private Sub UserForm_Initialize()
    
    ComboBox1.Text = GetSetting("Leidinglegprogramma", "Startup", "InvoerRolLengte", "")
    ComboBox1.SelStart = 0
    ComboBox1.SelLength = Len(ComboBox1.Text)
End Sub

Private Sub CommandButton1_Click()
    'EINDE PROGRAMMA
    
    ' SaveSetting "Leidinglegprogramma", "Startup", "InvoerRolLengte", ComboBox1.Text
    ' F_InvoerRollengte.Hide
    Unload Me
End Sub


Private Sub ComboBox1_Change()

    If ComboBox1.Text = "" Then
        CommandButton2.Enabled = False
    Else
        CommandButton2.Enabled = True
    End If
    
    Dim a As String
    Dim b As String
    a = ComboBox1.Text
    b = Val(ComboBox1.Text)
    
    If a <> b Then
        CommandButton2.Enabled = False
        MsgBox "Geen juiste waarde ingevuld.", vbCritical, "Let op"
    End If
    
    SaveSetting "Leidinglegprogramma", "Startup", "InvoerRolLengte", ComboBox1.Text
    
End Sub

Private Sub ComboBox1_KeyDown(ByVal Keycode As MSForms.ReturnInteger, ByVal Shift As Integer)
    'druk op enter of spatie

    If Keycode = 13 Or Keycode = 32 Then
        If ComboBox1.Text <> "" Then
            F_InvoerRollengte.Hide
            Call StartLengteProgramma(ComboBox1.Text)
        Else
            MsgBox "Geen Rollengte ingevuld"
        End If
    End If
End Sub


Private Sub CommandButton2_Click()
    
    Call StartLengteProgramma(ComboBox1.Text)
    SaveSetting "Leidinglegprogramma", "Startup", "InvoerRolLengte", ComboBox1.Text
End Sub

Sub StartLengteProgramma(Lengte As Double)
    Unload F_InvoerRollengte
    
    'MsgBox "Opgegeven rollengte: " & Lengte & " meter"
    
    '----------------------------------------------------------------------------------------
    'START BEPALEN ROLLENGTE
    '----------------------------------------------------------------------------------------
    
    ' invoer in meters, lijnen getekend in cm
    
    Lengte = Lengte * 100
    Call M_4BerekenKopStaartNW.BerekenKopStaart1(Lengte)

End Sub

Attribute VB_Name = "F_LengteMonitor"
Attribute VB_Base = "0{4C48B831-C8AE-4DEA-86F1-04384187087C}{0B1A1FA5-6FB2-4504-9301-FFC2CA956BE2}"
Attribute VB_GlobalNameSpace = False
Attribute VB_Creatable = False
Attribute VB_PredeclaredId = True
Attribute VB_Exposed = False
Attribute VB_TemplateDerived = False
Attribute VB_Customizable = False

'showmodal is in properties op TRUE gezet !

Dim bMetenOverslaan As Boolean



Private Sub CommandButton2_Click()
    '---------------------------------------------------
    'MEET LENGTE ('zie ook knop op: F_main)
    '---------------------------------------------------
    
    Call M_0SaveGetSettings.SaveSettings
    Call M_5BerekenLengteInLayers.BerekenLengteInColors
End Sub


Private Sub CommandButton3_Click()
    '---------------------------------------------------
    'STRETCH LEIDING ('zie ook knop op: F_main)
    '---------------------------------------------------
    Call M_7WijzigenLengte.WijzigenLengte
    Call MeetLengte
End Sub




Private Sub UserForm_Initialize()
    Label5.Caption = F_Main.TextBox1.Text
    bMetenOverslaan = False
    Call MeetLengte
End Sub

Private Sub Image1_Click()
    Call Afbeelding
End Sub

Private Sub Image2_Click()
    Call Afbeelding
    
End Sub
Sub Afbeelding()
        
    Image1.Visible = Not (Image1.Visible)
    Image2.Visible = Not (Image2.Visible)
    
    If Image1.Visible = True Then
        TextBox1.BackColor = vbGreen
        Call MeetLengte
    Else
        TextBox1.BackColor = vbRed
    End If
    
End Sub

Public Sub MeetLengte()
   
    'NIET METEN INDIEN AFBEELDING NIET-METEN ZICHTBAAR IS
    If Image1.Visible = False Then Exit Sub
    If F_LengteMonitor.Visible = False Then Exit Sub
    'MsgBox "meet lengte"

    Dim sAktieveLaag As String
    sAktieveLaag = ThisDrawing.ActiveLayer.Name
    
    Label1.Caption = "Lengte laag: " & sAktieveLaag
    TextBox1.BackColor = vbGreen
    Label2.Visible = False
    Label3.Visible = False
    
     
     Dim ssetObj As Object
    'Set ssetObj = ThisDrawing.SelectionSets.Add("SSET")
    
    Set ssetObj = CreateSelectionSet
  
    Dim gpCode(0) As Integer
    Dim dataValue(0) As Variant
    
    'groepscode 8 > laagnaam
    'groepscode 0 > entityname bijv Circle
    
    gpCode(0) = 8
    dataValue(0) = sAktieveLaag
    
    Dim groupCode As Variant, dataCode As Variant
    groupCode = gpCode
    dataCode = dataValue
    
    ssetObj.Select acSelectionSetAll, , , groupCode, dataCode
    
    Dim element As Object
    Dim dLengte As Double
    Dim dReserveLengte As Double
       
    
    
    Dim bFout As Boolean
    
    For Each element In ssetObj
        Select Case element.EntityName
        Case "AcDbLine"
            dLengte = dLengte + element.Length
        Case "AcDbArc"
            dLengte = dLengte + element.ArcLength
        Case "AcDbPolyline"
            TextBox1.BackColor = vbRed
            element.Highlight True
            
            If bFout <> True Then
                Label2.Visible = True
                Label3.Visible = True
            End If
            
        Case Else
        
        End Select
        
    Next element
    
        
    dLengte = dLengte / 100
    dLengte = Round(dLengte, 1)
    
    dReserveLengte = Label5.Caption
    
    
    TextBox1.Text = dLengte
    Label6.Caption = Round(dReserveLengte + dLengte, 1)
    ' ThisDrawing.SetVariable "MODEMACRO", Str(dLengte) & " m"
    
    ssetObj.Clear
    ssetObj.Delete
    

End Sub

Public Function CreateSelectionSet(Optional ssName As String = "ss") As AcadSelectionSet

    Dim ss As AcadSelectionSet
    
    On Error Resume Next
    Set ss = ThisDrawing.SelectionSets(ssName)
    If Err Then Set ss = ThisDrawing.SelectionSets.Add(ssName)
    ss.Clear
    Set CreateSelectionSet = ss

End Function


Private Sub UserForm_Terminate()
   bMetenOverslaan = True
End Sub


Private Sub CommandButton1_Click()

'----------------------------------------------------------------------
'GESELECTEERDE LAAG AKTIEF MAKEN
'----------------------------------------------------------------------

   
    Dim ReturnObj1 As AcadEntity
    Dim basePnt1 As Variant
    
    On Error Resume Next
    
    ThisDrawing.Utility.GetEntity ReturnObj1, basePnt1, "Selecteer een object."
    If Err <> 0 Then
        Err.Clear
        Exit Sub
    End If
                    
    If ThisDrawing.Layers.Item(ReturnObj1.Layer).Freeze = True Then ThisDrawing.Layers.Item(ReturnObj1.Layer).Freeze = False
    
    
    ThisDrawing.ActiveLayer = ThisDrawing.Layers.Item(ReturnObj1.Layer)
    
    Label1.Caption = "Lengte laag: " & ThisDrawing.ActiveLayer.Name
    
    'meetfunctie aanzetten
    Image1.Visible = True
    Image2.Visible = False
    
    Call MeetLengte
    
End Sub

Attribute VB_Name = "F_Main"
Attribute VB_Base = "0{6E5E7793-A7E8-48F7-A205-D86F24C2FC30}{8F89D80E-0FED-4BA7-B223-E9F59D2E37EA}"
Attribute VB_GlobalNameSpace = False
Attribute VB_Creatable = False
Attribute VB_PredeclaredId = True
Attribute VB_Exposed = False
Attribute VB_TemplateDerived = False
Attribute VB_Customizable = False

'''''
'''''    ' Display the delta of the new line
'''''    lineDelta = lineObj.Delta
'''''    MsgBox "The delta of the new Line is: " & vbCrLf & _
'''''                                            "DeltaX:" & lineDelta(0) & vbCrLf & _
'''''                                            "DeltaY:" & lineDelta(1) & vbCrLf & _
'''''                                            "DeltaZ:" & lineDelta(2)
'''''











Private Sub CommandButton33_Click()

    'NIEUW 31 MAART 2003
    
    ' --------------------------------------------------------------
    ' SELECTEREN ARC
    ' --------------------------------------------------------------
    
    F_Main.Hide
    
    Dim ReturnObj1 As AcadArc
    Dim basePnt1 As Variant
    
    On Error Resume Next
    
    ThisDrawing.Utility.GetEntity ReturnObj1, basePnt1, "Selecteer de aanvoer-polyline."
    If Err <> 0 Then
        Err.Clear
        'MsgBox "Verkeerd geselecteerd"
        Exit Sub
    End If
            
    If ReturnObj1.EntityName <> "AcDbArc" Then
        MsgBox "Geen Arc geselecteerd.", vbCritical, "Let op"
        Exit Sub
    End If
     
    'MsgBox basePnt1(0) & Chr(10) & Chr(13) & basePnt1(1) & Chr(10) & Chr(13) & basePnt1(2)
    
    
    ' --------------------------------------------------------------
    ' SELECTEREN NIEUWE PLAATSINGSPUNT
    ' --------------------------------------------------------------
    
    'LET OP: SNAPANG IN RADIALEN !
    'ThisDrawing.SetVariable "ORTHO", "ON"
    ThisDrawing.SetVariable "SNAPANG", ReturnObj1.StartAngle
    
    Dim p As Variant
    p = ThisDrawing.Utility.GetPoint(basePnt1, "Selecteer het plaatsingspunt")
    
    ThisDrawing.SetVariable "SNAPANG", 0
    
    ' --------------------------------------------------------------
    ' BEREKENEN LENGTE-VERSCHIL
    ' --------------------------------------------------------------
    
    Dim dLengte As Double
    dLengte = Lengte(basePnt1, p)
    
    ' --------------------------------------------------------------
    ' BEPALEN VERLENGEN OF VERKORTEN
    ' --------------------------------------------------------------
    
    Dim bVerlengen As Boolean
    If Lengte(p, ReturnObj1.EndPoint) > Lengte(p, basePnt1) Then
        bVerlengen = True
        MsgBox "verlengen"
    Else
        bVerlengen = False
        MsgBox "inkorten"
    End If
        
   
    ' --------------------------------------------------------------
    ' ALLE VOORGAANDE SELECTIESETS VERWIJDEREN
    ' --------------------------------------------------------------
    'geeft soms fatale error !
    'Call SelectiesetsVerwijderen
    
    ' --------------------------------------------------------------
    ' AANMAKEN SELECTIESET OM EINDPUNT ARC (ZOEK LIJN)
    ' --------------------------------------------------------------
   
    'Aanmaken selectieset
    
    Dim ReturnEindpunt As Variant
    Dim p1(0 To 2) As Double
    Dim p2(0 To 2) As Double
    
    ReturnEindpunt = ReturnObj1.EndPoint

    p1(0) = ReturnEindpunt(0) - 0.1
    p1(1) = ReturnEindpunt(1) - 0.1
    p1(2) = 0
    p2(0) = ReturnEindpunt(0) + 0.1
    p2(1) = ReturnEindpunt(1) + 0.1
    p2(2) = 0
    
    Dim ssetObj As AcadSelectionSet
    Set ssetObj = ThisDrawing.SelectionSets.Add("SSET")
    If Err Then
        ssetObj.Clear
        ssetObj.Delete
        End
    End If
    
    ssetObj.Select acSelectionSetCrossing, p1, p2
    
    
    ' --------------------------------------------------------------
    ' UITLEZEN SELECTIESET EN VINDEN LIJN
    ' --------------------------------------------------------------

    Dim element As Object
    Dim LijnObj1 As AcadLine
    Dim sVorigeHandle As String

    sVorigeHandle = ReturnObj1.handle

    For Each element In ssetObj
        element.Color = acGreen

        If element.handle <> sVorigeHandle Then
            If element.EntityName = "AcDbLine" Then
                    'element.Highlight True
                    LijnTeller = LijnTeller + 1
                    Set LijnObj1 = element
            End If
        End If
    Next element

    ssetObj.Clear
    ssetObj.Delete
    
    If LijnTeller = 0 Then
        MsgBox "Geen lijnen (leidingen) aan de arc verbonden.", vbExclamation, "let op"
        End
    End If
    
      
   
    
    
    ' --------------------------------------------------------------
    ' INKORTEN LIJN
    ' --------------------------------------------------------------
    
    'MsgBox LijnObj1.handle
    Dim dNieuweLengte As Double
    
    If bVerlengen = True Then
        dNieuweLengte = LijnObj1.Length + dLengte
    Else
        dNieuweLengte = LijnObj1.Length - dLengte
    End If
    

    If LijnTeller = 1 Then
        If Lengte(LijnObj1.EndPoint, p) > Lengte(LijnObj1.StartPoint, p) Then
            Call LijnlengteWijzigen(LijnObj1, dNieuweLengte, False)
        Else
            Call LijnlengteWijzigen(LijnObj1, dNieuweLengte, True)
        End If
    End If
    
    
    ' --------------------------------------------------------------
    '  VERPLAATSEN ARC
    ' --------------------------------------------------------------
    
    'BEPALEN OF BEGIN- OF EINDPUNT VAN LIJN GEVONDEN IS
    
    
    If Lengte(LijnObj1.EndPoint, ReturnObj1.EndPoint) Then
        'Beginpunt Lijn Gevonden
        ReturnObj1.Move ReturnObj1.EndPoint, LijnObj1.EndPoint
    Else
        'Eindpunt Lijn Gevonden
        ReturnObj1.Move ReturnObj1.EndPoint, LijnObj1.StartPoint
    End If
    
    
    

    
End Sub













Private Sub CommandButton37_Click()
    
    Me.Hide
    
    On Error Resume Next
    F_LengteMonitor.show
    If Err Then
        Err.Clear
    End If
    
End Sub






' OPROEPEN ABOUTBOX
Private Sub Image1_Click()
    F_About.show
End Sub
Private Sub Image11_Click()
    F_About.show
End Sub
Private Sub Label17_Click()
    F_About.show
End Sub
Private Sub Label26_Click()
     F_About.show
End Sub

Private Sub CommandButton34_Click()
    Me.Hide
    M_6PlaatsenSlingers.OpvragenHOH
End Sub








Private Sub TextBox1_Change()
    ' ebr 14 juni 2004
    
    If GetalIsDouble(TextBox1.Text) = False Then
        TextBox1.BackColor = vbRed
        MsgBox "Geen juist getal ingevuld (gebruik een punt maar geen komma).", vbCritical, "Let op"
        F_LengteMonitor.Label5.Caption = 0
    Else
        TextBox1.BackColor = vbWhite
        F_LengteMonitor.Label5.Caption = TextBox1.Text
    End If
    
End Sub

'returnPnt = ThisDrawing.Utility.GetCorner(basePnt, "Enter Other corner: ")
'ThisDrawing.Utility.AngleFromXAxis
'THISDRAWING.HandleToObject
'ThisDrawing.Utility.TranslateCoordinates



Private Sub UserForm_Initialize()
    
    Call M_0SaveGetSettings.GetSettings
    Call LeesCfgFile

End Sub


Private Sub UserForm_Activate()
    'MsgBox "activate"
End Sub


Private Sub CommandButton28_Click()
    'TEST WERKING BEPALEN VAN: TEKEN_LIJN_OVER_POLYLINE EN BEPALEN SNIJPUNT_POLYLINE

    Dim plineObj As AcadLWPolyline
    Dim LijnObj As AcadLine
    
    Set plineObj = ThisDrawing.ModelSpace.Item(0)
    Set LijnObj = ThisDrawing.ModelSpace.Item(1)

    Call M_4BepalenLengteNEW.TekenLijnenOverPolyline(plineObj)
    Call M_4BepalenLengteNEW.BepalenSnijpunt(plineObj, LijnObj)
    Call M_4BepalenLengteNEW.VerwijderenLosseLines
    
End Sub



Private Sub CommandButton24_Click()
    M_TekenenAftaklijnen.StartTekenenAftaklijnen
End Sub

Private Sub CommandButton26_Click()
    ThisDrawing.SetVariable "LIMCHECK", 0      'limits off
    Call M_0SaveGetSettings.SaveSettings
    Call M_3PlaatsenArcsNew.PlaatsenArcsNew
    ThisDrawing.SetVariable "LIMCHECK", 1      'limits on
    End
End Sub



Private Sub CommandButton30_Click()

    For Each element In ThisDrawing.ModelSpace
         
        If element.EntityName = "AcDbLine" Then
            Call Punt1(element.StartPoint, 1)
            
        End If
                  
        If element.EntityName = "AcDbArc" Then
            'Call Punt1(Element.StartPoint, 2)
        End If
        
    Next element
End Sub





'**********************************************************************************************
'ONDERSTAANDE GEDEELTE: VOOR HET SELECTREREN VAN ROLTYPEN EN ROLLENGTEN
'**********************************************************************************************

Private Sub ComboBox3_Change()
    Call M_0CfgFiles.ChangeRollengten
End Sub


''''UITGEZET OP 6 MAART 2003:
''''
'''''''''' VERWIJDERD 24 FEB 2003
''''Private Sub CommandButton1_Click()
''''   Call PlaatsenBochten
''''End Sub
''''
''''Sub PlaatsenBochten()
''''
''''    ' -----------------------------
''''    ' Teken een hatch (legpatroon), deze vervolgens exploderen (eerste overige elementen verwijderen)
''''    ' daarna programma runnen.
''''    '----------------------------------------
''''
''''    MsgBox "FilterenLijnen IS VERWIJDERD"
''''    'Call FilterenLijnen
''''
''''
''''    'Laat handles zien: 'F_Main.Show
''''    'F_Main.Show
''''
''''    Dim HoHafstand As Double
''''    HoHafstand = F_Main.ComboBox2.Text
''''    Call VerbindLijnenMetArc(HoHafstand / 2)    ' principe zie: Call VerbindLijnen
''''End Sub



Private Sub CommandButton10_Click()
    Call M_0SaveGetSettings.SaveSettings
    F_Main.Hide
        
    
    F_LengteMonitor.Image1.Visible = True
    F_LengteMonitor.Image2.Visible = False
    
    'MsgBox "dit weggehaald op 27 mei 2004"
    'Unload Me
    
    'End ' dit weggehaald op 27 jan 2004
End Sub



Private Sub CommandButton12_Click()
    MsgBox "6 MAART 2003: KAN WEG ???", vbInformation

    Dim objPline As Object
    Set objPline = ThisDrawing.ModelSpace.Item(ThisDrawing.ModelSpace.Count - 1)

    MsgBox BepaalLijnAanEindePolyline(objPline)
    
End Sub



Private Sub CommandButton2_Click()
    MsgBox "6 MAART 2003: KAN WEG ???", vbInformation
    
    Dim sLogFile As String
    sLogFile = "C:\Temp\WTH-logfile.txt"
    If Dir(sLogFile) <> "" Then Kill (sLogFile)         'verwijderen voorgaande logfile
    
    Call BerekenRollengte
End Sub




Private Sub CommandButton5_Click()

    Dim AantalElementVoorHethatchen As Double
    AantalElementVoorHethatchen = ThisDrawing.ModelSpace.Count
    
    Call M_0SaveGetSettings.SaveSettings
    Call PlaatsenHatch
    Call AlleLijnenInkorten(AantalElementVoorHethatchen)
    
    ThisDrawing.Regen (True)
    ThisDrawing.Application.Update
    
    '24 feb 2003 verwijderd en nieuwe routine gemaakt:
    'Call PlaatsenBochten
    
    Call M_3PlaatsenArcsNew.PlaatsenArcsNew
End Sub

Private Sub CommandButton6_Click()
    Call M_0SaveGetSettings.SaveSettings
    Call BepaalObstakels(True)
End Sub


Private Sub CommandButton7_Click()
    MsgBox "DE OUDE ROUTINE IS VERWIJDERD (ZIE TXT-BACKUP)"
    'Call BerekenKopStaart
End Sub


Private Sub CommandButton9_Click()
    
    'SHOW LOGFILE
    Dim sAntw As String
    antw = MsgBox("Openen WTH-logfile ?", vbCritical + vbYesNo, "WTH-logfile.txt")
    
    If antw = vbNo Then Exit Sub
    Shell "notepad.exe C:\Temp\WTH-logfile.txt", vbMaximizedFocus
End Sub

Private Sub CommandButton35_Click()
    'SHOW ROLLENGTEN.CFG
    Dim sAntw As String
    antw = MsgBox("Configuratie-bestand met rollengten wijzigen ?", vbCritical + vbYesNo, "Rollengten.cfg")
    
    If antw = vbNo Then Exit Sub

    sCfgFile = FindZoekpad("Rollengten.cfg")
    Shell "notepad.exe " & sCfgFile, vbMaximizedFocus
End Sub

Private Sub CommandButton14_Click()
   Call OpschuivenLegpatroon
End Sub

Sub OpschuivenLegpatroon()
    '* nieuwe sub 21 mei 2003
    Call M_0SaveGetSettings.SaveSettings
    Call M_6TrimmenLijnen.TrimmenLijnen
End Sub

Private Sub CommandButton31_Click()
    Call M_0SaveGetSettings.SaveSettings
    Call OffsetPoly
End Sub


Private Sub CommandButton21_Click()
    Call M_0SaveGetSettings.SaveSettings
    Call M_5BerekenLengteInLayers.BerekenLengteInColors
End Sub



Private Sub CommandButton29_Click()

    'MsgBox "*** 5 mei 2004 deze regel ertussen gezet"
    Call M_0CfgFiles.ChangeRollengten
        
    Call M_0SaveGetSettings.SaveSettings
    
    ' --------------------------------------------------------------
    ' CONTROLEREN RESERVE LENGTE (SNIT)
    ' --------------------------------------------------------------
    On Error Resume Next
    Dim dSnit As Double
    dSnit = F_Main.TextBox1.Text
    If Err Then
        Err.Clear
        MsgBox "De ingevoerde reservelengte (snit) is niet juist.", vbCritical, "Let op"
        Exit Sub
    End If
    ' --------------------------------------------------------------
    
    Load F_InvoerRollengte
    F_InvoerRollengte.Label3.Caption = F_Main.ComboBox3.Text
   
    F_InvoerRollengte.show
    
End Sub





Private Sub CommandButton36_Click()
    Call M_7WijzigenLengte.WijzigenLengte
    Call F_LengteMonitor.MeetLengte
End Sub



Private Sub UserForm_Deactivate()
    'automatisch meten met lengte monitor tijdelijk uitzetten
        'MsgBox "de-activate"
    
        'F_LengteMonitor.Image1.Visible = True
        'F_LengteMonitor.Image2.Visible = False
    
End Sub

Attribute VB_Name = "F_TrimPolyline_TEST"
Attribute VB_Base = "0{D3AC02F1-6EEB-48A4-90CE-09E76E2425D5}{1BC395D0-7FC4-45DD-AE2B-8D17772208D1}"
Attribute VB_GlobalNameSpace = False
Attribute VB_Creatable = False
Attribute VB_PredeclaredId = True
Attribute VB_Exposed = False
Attribute VB_TemplateDerived = False
Attribute VB_Customizable = False

Private Sub CommandButton1_Click()
    Call TrimPolyline2(ThisDrawing.ModelSpace.Item(0), 80, 0, 0)
End Sub

Public Sub TrimPolyline2(objPline As Object, InvoerLengte, LaatsteX, LaatsteY)
     
    'WERKING:
    'ALS X = 0 EN Y = 0 DAN ZAL HET LAATSTE LIJNSTUK ZIJN OORSPRONKELIJKE LENGTE BEHOUDEN
    'ALS X <> 0 OF Y <> 0 DAN ZAL HET LAATSTE LIJNSTUK TOT HET OPGEGEVEN COORDINAAT WORDEN VERKORT
    
    'MsgBox objPline.handle
    
    '-------------------------------------------------------------------------------------
    'DIT PROGRAMMA BEREKEND DE LENGTE VAN EEN LWT-POLYLINE
    '-------------------------------------------------------------------------------------
            
    
    If objPline.EntityName <> "AcDbPolyline" Then
        MsgBox "Het geslecteerde element is geen LWT-Polyline", vbCritical, "Let op"
        Exit Sub
    End If
       
    
    Dim intVCnt As Integer  'interval counter
    Dim varCords As Variant
    Dim varVert As Variant  'vertexen
    Dim varCord As Variant
    Dim varNext As Variant
    Dim intCrdCnt As Integer
    Dim dLengte As Double
    Dim dblArc As Double
    Dim dblAng As Double
    Dim dblChord As Double
    Dim dblInclAng As Double
    Dim dblRad As Double
    
    Dim LaatsteVertex As Integer
    
      
    varCords = objPline.Coordinates
    
    'AANTAL VERTEXEN (COORDINATEN VAN POLYLINE)
    For Each varVert In varCords
      intVCnt = intVCnt + 1
    Next
     
    Dim punten() As Double      'LET OP, MOET ALS DOUBLE ANDERS ERROR BIJ AddLightWeightPolyline(punten) !
    ReDim punten(0)
       
            
    For intCrdCnt = 0 To intVCnt / 2 - 1                'For LWPoly 2 - 1 else 3 -1
      If intCrdCnt < intVCnt / 2 - 1 Then               'noodzakelijk anders error bij een enkele polyline
      
                '-------------------------------------------------------------------------
                'BEPAAL LIJN-LENGTE (INDIEN GETBULGE = 0, DAN GEEN ARC)
                '-------------------------------------------------------------------------
            
                If objPline.GetBulge(intCrdCnt) = 0 Then
                  varCord = objPline.Coordinate(intCrdCnt)
                  varNext = objPline.Coordinate(intCrdCnt + 1)
                  
                  dLengte = dLengte + Sqr(((varCord(0) - varNext(0)) ^ 2) + ((varCord(1) - varNext(1)) ^ 2))
                                          
                Else
                
                '-------------------------------------------------------------------------
                'BEPAAL ARC-LENGTE (INDIEN GETBULGE <> 0, DAN ARC)
                '-------------------------------------------------------------------------
                    varCord = objPline.Coordinate(intCrdCnt)
                    varNext = objPline.Coordinate(intCrdCnt + 1)
                    dblChord = Sqr(((varCord(0) - varNext(0)) ^ 2) + ((varCord(1) - varNext(1)) ^ 2))
                    
                    'Bulge is the tangent of 1/4 of the included angle between
                    'vertices. So we reverse the process to get the included angle
                    dblInclAng = Atn(Abs(objPline.GetBulge(intCrdCnt))) * 4
                    dblAng = (dblInclAng / 2) - ((Atn(1) * 4) / 2)
                    dblRad = (dblChord / 2) / (Cos(dblAng))
                    dblArc = dblInclAng * dblRad
                    dLengte = dLengte + dblArc
                End If
                
                
                
                
           
                ' ***********************************************************
                ' *** UITBREIDING 26 FEB 2003 DOOR EBR: OPSLAAN VERTEXEN: ***
                ' ***********************************************************
                
                'MsgBox "x=" & varCord(0) & "   y=" & varCord(1)
                
                'NIEUW VERTEXEN ARRAY
                If intCrdCnt = 0 Then
                    punten(UBound(punten)) = varCord(0)
                    ReDim Preserve punten(UBound(punten) + 1)
                    punten(UBound(punten)) = varCord(1)
                Else
                    ReDim Preserve punten(UBound(punten) + 1)
                    punten(UBound(punten)) = varCord(0)
                    ReDim Preserve punten(UBound(punten) + 1)
                    punten(UBound(punten)) = varCord(1)
                End If
                                 
                LaatsteVertex = intCrdCnt
                If dLengte > InvoerLengte Then Exit For
            
            
        End If
    Next intCrdCnt
      
    'WEERGEVEN LENGTE IN FUNCTIEAANROEP:
    'LengtePolyline2 = dLengte
    
    MsgBox "LaatsteVertex=" & LaatsteVertex
    MsgBox "Lengte verschil=" & dLengte - InvoerLengte
    
    'OPSLAAN LAATSTE TWEE VERTEXEN
    ReDim Preserve punten(UBound(punten) + 1)
    punten(UBound(punten)) = varNext(0)
    ReDim Preserve punten(UBound(punten) + 1)
    punten(UBound(punten)) = varNext(1)
    
    '-------------------------------------------------------------------------
    'AFBEELDEN VERTEXEN POLYLINE (DEBUG)
    '------------------------------------------------------------------------
    
'    For t = LBound(punten) To UBound(punten)
'        MsgBox punten(t), vbExclamation
'    Next t
        
    '-------------------------------------------------------------------------
    'TEKEN NIEUWE POLYLINE (MET DE JUISTE LENGTE)  25 FEB 2003
    '-------------------------------------------------------------------------
           
    
    'TEKENEN NIEUWE GETRIMDE POLYLINE:
    Dim NieuwPoly As AcadLWPolyline
    Set NieuwPoly = ThisDrawing.ModelSpace.AddLightWeightPolyline(punten)
    NieuwPoly.Color = acRed
    NieuwPoly.Update
    
    'NADERHAND ARCS (BULGES) IN POLYLINE PLAATSEN:
    varCords = NieuwPoly.Coordinates
    For Each varVert In varCords
      intVCnt = intVCnt + 1
    Next
    
    'If LaatsteVertex = 0 Then LaatsteVertex = intCrdCnt + 2

    For intCrdCnt = 0 To LaatsteVertex - 1
         NieuwPoly.SetBulge intCrdCnt, objPline.GetBulge(intCrdCnt)
    Next intCrdCnt
    
  
    
    
End Sub







Private Sub CommandButton3_Click()
'WERKT NIET: GEEFT ERROR
Dim Obj As AcadEntity

SelecterenObject ("Selecteer leiding")
Obj.Color = acYellow

End Sub
Sub SelecterenObject(sBeschrijving As String) 'As AcadEntity

    'Dim ReturnObj1
    Me.Hide
    
    ThisDrawing.Utility.GetEntity ReturnObj1, basePnt1, sBeschrijving
    If Err <> 0 Then
        Err.Clear
        MsgBox "Verkeerd geselecteerd"
        Exit Sub
    End If
    
    If UCase(ReturnObj1.EntityName) <> ObjecType Then
        MsgBox "Verkeerde element geselecteer", vbCritical, "Let op"
        Exit Sub
    End If
    
    Set SelecterenObject = ReturnObj1
    
End Sub

Attribute VB_Name = "M_0Algemeen"

'--------------------------------------------------------------------------------------------
' DE VOLGENDE SUBS EN FUNCTIONS ZIJN AANWEZIG:
'--------------------------------------------------------------------------------------------
' Public Function Lengte(P1 As Variant, p2 As Variant) As Double
' Public Sub LijnlengteWijzigen(LijnObj As AcadLine, dNieuweLengte As Double, bEindpuntInkorten As Boolean)
' Public Sub InsertBlock(Blocknaam, PInsert, sLaagnaam)
' Public Sub AanmakenLaag(Laagnaam As String, KleurNr As Integer, MaakAktief As Boolean)
' Public Sub SelectiesetsVerwijderen()
' Public Function BepalenVanSnijpunt(element1 As Object, element2 As Object, ExtendOption As Integer) As Variant
' Public Sub Punt(P)
' Public Sub Punt1(P, kleur)
' Public Sub VerwijderenLogFile()
' Public Sub SchrijfLogFile(Tekst As String)
' Public Function ZoekElementHandleRondPunt(P As Variant, dCrossingSelectieGrootte As Double) As String
' Public Sub ZoomInOpElement(element As AcadEntity, bHighlight As Boolean)
' Function GetalIsDouble(sGetal As String, Optional sMelding As String) As Boolean



Public Function Lengte(p1 As Variant, p2 As Variant) As Double

    'FUNCTIE VOOR HET BEREKENEN VAN DE AFSTAND TUSSEN TWEE PUNTEN
    
    Dim DX As Double
    Dim DY As Double
    
    DX = Abs(p2(0) - p1(0))
    DY = Abs(p2(1) - p1(1))

    Lengte = Sqr((DX ^ 2) + (DY ^ 2))
End Function

Public Sub LijnlengteWijzigen(LijnObj As AcadLine, dNieuweLengte As Double, bEindpuntInkorten As Boolean)

'EBR 28 MAART 2003

'--------------------------------------------------------------------------------------------
' DE VOLGENDE SUBROUTINE WIJZIGD DE LENGTE VAN EEN LIJN T.O.V. BEGIN- OF EINDPUNT
'--------------------------------------------------------------------------------------------

    'VOORBEELD AANROEP: Call LijnlengteWijzigen(ThisDrawing.ModelSpace.Item(0), 70, True)
    
    Dim dDraaipunt As Variant
    Dim dDraaiHoek As Double
    Dim p As Variant
    
    dDraaipunt = LijnObj.StartPoint
    dDraaiHoek = LijnObj.Angle
    LijnObj.Rotate dDraaipunt, -dDraaiHoek

    If bEindpuntInkorten = True Then
        p = LijnObj.StartPoint
        p(0) = p(0) + dNieuweLengte
        LijnObj.EndPoint = p
    Else
        p = LijnObj.EndPoint
        p(0) = p(0) - dNieuweLengte
        LijnObj.StartPoint = p
    End If
    
    LijnObj.Rotate dDraaipunt, dDraaiHoek
        

End Sub


Public Sub InsertBlock(Blocknaam, PInsert, sLaagNaam)
        
'EBR 28 MAART 2003

'--------------------------------------------------------------------------------------------
' DE VOLGENDE SUBROUTINE PLAATST BLOCK IN DE TEKENING
' DE BLOCKNAAM MAG ZOWEL MET HOOFD- ALS KLEINE LETTERS INGEGEVEN WORDEN
' INDIEN HET BLOCK NIET IN DE TEKEING BESTAAT DAN ZAL DEZE UIT DE SUPPORT-DIRECTORY
' OF DE ACAD-APPLICATIONS DIRECTORY WORDEN GELEZEN.

' DEZE SUBROUTINE MAAKT GEBRUIK VAN: CALL AANMAKENLAGEN EN FINDZOEKPAD
'--------------------------------------------------------------------------------------------


        'AANROEP: InsertBlock "pijl", Pins, "0"
        'Ingevoerde blocknaam zal altijd worden geconverteerd naar hoofdletters.

        'CONTROLE OF DE BLOCKNAME (DEFENITIE) IN DE TEKENING VOORKOMT
        Dim sBlockNaam As String
        Dim bBlockInTekening As Boolean
        Dim Block As AcadBlock
        
        For Each BlockObj In ThisDrawing.Blocks
            If UCase(BlockObj.Name) = UCase(Blocknaam) Then
                bBlockInTekening = True
                sBlockNaam = BlockObj.Name
                'bBlockInTekening = True
            End If
        Next
        
        'SYMBOOL INSERTEN
        Dim BlockRefObj As AcadBlockReference
        
        If bBlockInTekening = True Then
            Set BlockRefObj = ThisDrawing.ModelSpace.InsertBlock(PInsert, sBlockNaam, 1, 1, 1, 0)
        Else
            'WBLOCK UIT DE ACAD-ZOEKPADEN
            sBlockNaam = Blocknaam & ".dwg"
            sBlockNaam = FindZoekpad(sBlockNaam)
            'MsgBox sBlockNaam
            
            If sBlockNaam = "ERROR" Then
                MsgBox "Het symbool (block) " & Blocknaam & " staat niet in de zoekpaden van AutoCAD.", vbCritical, "Block kan niet worden geplaatst."
                Exit Sub
            Else
                Set BlockRefObj = ThisDrawing.ModelSpace.InsertBlock(PInsert, sBlockNaam, 1, 1, 1, 0)
                'BlockObj.Layer = "0"
                'BlockObj.Update
            End If
        End If
        
        Dim sNieuwLaagnaam As String
        sNieuwLaagnaam = sLaagNaam
        Call AanmakenLaag(sNieuwLaagnaam, 7, False)
        
        BlockRefObj.Layer = sLaagNaam
        BlockRefObj.Update
        
         'oude routine:
'        Dim sAppPath As String
'        sAppPath = Application.Path
'
'        If Dir(sAppPath & "\pijl.dwg") = "" Then
'            MsgBox "Geen symbool PIJL.DWG in het zoekpad " & sAppPath & " aanwezig.", vbExclamation, "leidinglegprogramma"
'        Else
'            Dim BlockObj As AcadBlockReference
'            Set BlockObj = ThisDrawing.ModelSpace.InsertBlock(PInsert, sAppPath & "\pijl.dwg", 1, 1, 1, 0)
'            BlockObj.Layer = "0"
'            BlockObj.Update
'        End If
        

        
        
        
        
End Sub

Public Sub AanmakenLaag(LaagNaam As String, KleurNr As Integer, MaakAktief As Boolean)

    Dim LaagObj As AcadLayer
    Dim LaagGevonden As Boolean
    Dim NwLaagObj As AcadLayer
    
    For Each LaagObj In ThisDrawing.Layers
        If UCase(LaagObj.Name) = LaagNaam Then LaagGevonden = True
    Next LaagObj
    
    If LaagGevonden = False Then
        Set NwLaagObj = ThisDrawing.Layers.Add(LaagNaam)
        NwLaagObj.Color = KleurNr
    End If
    
    On Error Resume Next
    If MaakAktief = True Then ThisDrawing.ActiveLayer = ThisDrawing.Layers.Item(LaagNaam)
    If Err Then
        Err.Clear
        MsgBox "Laag ' " & LaagNaam & " ' kan niet aktief worden gemaakt.", vbExclamation, "Let op"
    End If

End Sub


Public Sub SelectiesetsVerwijderen()

    Dim ssetObj As AcadSelectionSet
    
    For Each ssetObj In ThisDrawing.SelectionSets
        ssetObj.Clear
        ssetObj.Delete
    Next ssetObj
    
End Sub


Public Function BepalenVanSnijpunt(element1 As Object, element2 As Object, ExtendOption As Integer) 'As Variant

'26 feb 2003 EBR
'21 mei 2003: het eerste snijpunt met een polyline is het snijpunt wat het dichtst bij het
'             beginpunt van die polyline bevindt (dus rekend vanaf beginpunt) !!

'   0 = acExtendNone
'   1 = acExtendThisEntity
'   2 = acExtendOtherEntity
'   3 = acExtendBoth

'   Voorbeeld gebruik:  Snijpunt = BepalenVanSnijpunt(element1, element2, 3)
'                       Dim PuntObj As AcadPoint
'                       Set PuntObj = ThisDrawing.ModelSpace.AddPoint(vSnijpunt)

' -----------------------------------------------------------------------
'   BEREKENEN INTERSECTIE (SNIJPUNT) VAN TWEE LIJNEN
' -----------------------------------------------------------------------

    Dim intPoints As Variant
    Dim vSnijpunt(0 To 2) As Double
    
    Select Case ExtendOption
    Case 0
        'Does not extend either object.
        intPoints = element1.IntersectWith(element2, acExtendNone)
    Case 1
        'Extends the base object.
        intPoints = element1.IntersectWith(element2, acExtendThisEntity)
    Case 2
        'Extends the object passed as an argument.
        intPoints = element1.IntersectWith(element2, acExtendOtherEntity)
    Case 3
        'Extends both objects.
        intPoints = element1.IntersectWith(element2, acExtendBoth)
    End Select
     

    Dim I As Integer, j As Integer, k As Integer
    Dim str As String
    If VarType(intPoints) <> vbEmpty Then

        For I = LBound(intPoints) To UBound(intPoints)
            'str = "Intersection Point[" & k & "] is: x=" & intPoints(j) & "   y=" & intPoints(j + 1) & "   z=" & intPoints(j + 2)
            'MsgBox str: str = ""
            
            vSnijpunt(0) = intPoints(j)
            vSnijpunt(1) = intPoints(j + 1)
            vSnijpunt(2) = 0
            'MsgBox vSnijpunt(0) & "      " & vSnijpunt(1), vbCritical
            
            I = I + 2
            j = j + 3
            k = k + 1   'geeft aantal snijpunten aan
            
            '** NIEUW 21 MEI 2003: PAKT ALTIJD HET LAATSTE SNIJPUNT (IS VERSTE VANAF BEGINPUNT VAN POLYLINE !!!)
            'vSnijpunt = intPoints
            
            
            
        Next
    End If

' -----------------------------------------------------------------------
'   CONTROLE OP HET AANTAL SNIJPUNTEN
' -----------------------------------------------------------------------
        
    If k = 0 Then
        '*** deze melding uitgezet op 27 jan 2004
        MsgBox "Leiding heeft geen snijpunt met de aanvoer/ retourleiding", vbCritical, "Let op"
        Exit Function
    End If
    
    If k = 1 Then
        'vSnijpunt = intPoints         '* uitgezet op 21 mei 2003, anders wordt laatste snijpunt gepakt ipv eerste !
    End If

'    If k > 1 Then
'        MsgBox "Leiding heeft meerdere snijpunten met de aanvoer/ retourleiding", vbCritical
'        '21 mei 2003 uitgezet (was origineel)
'        'Exit Function
'    End If

' --------------------------------------------------------------------------------------------
'   SNIJPUNT WEERGEVEN
' --------------------------------------------------------------------------------------------
    
    'MsgBox vSnijpunt(0) & "   " & vSnijpunt(1), vbExclamation
    'Call Punt1(vSnijpunt, 1)
    
'    Dim PuntObj As AcadPoint
'    Dim Ppunt(0 To 2) As Double
'    Ppunt(0) = vSnijpunt(0)
'    Ppunt(1) = vSnijpunt(1)
'    Ppunt(2) = 0
'    Set PuntObj = ThisDrawing.ModelSpace.AddPoint(Ppunt)
    
    
    
    'MsgBox "Het laatste snijpunt is: " & vSnijpunt(0) & "   " & vSnijpunt(1), vbInformation
    
    BepalenVanSnijpunt = vSnijpunt

End Function


Public Sub Punt(p)
    '--------------------------------------------------------------------------------------------
    ' PUNT TEKENEN EN PD-MODE INSTELLEN
    '--------------------------------------------------------------------------------------------
    Dim PuntObj As AcadPoint
    Dim iKleur As Integer
    
    Set PuntObj = ThisDrawing.ModelSpace.AddPoint(p)
    PuntObj.Update
    
    ThisDrawing.SetVariable "PDMODE", 32
    ThisDrawing.Regen acAllViewports
End Sub
Public Sub Punt1(p, kleur)
    '--------------------------------------------------------------------------------------------
    ' PUNT TEKENEN MET KLEUR EN PD-MODE INSTELLEN
    '--------------------------------------------------------------------------------------------
    Dim PuntObj As AcadPoint
    Dim iKleur As Integer
    
    Set PuntObj = ThisDrawing.ModelSpace.AddPoint(p)
    
    iKleur = kleur
    
    PuntObj.Color = iKleur
    PuntObj.Update
    
    ThisDrawing.SetVariable "PDMODE", 32
    'ThisDrawing.Regen acAllViewports
End Sub

Public Sub TekenLijn(Pbegin As Variant, Peind As Variant, LaagNaam As String)
    MsgBox Pbegin(0) & "     " & Pbegin(1)
    MsgBox Peind(0) & "     " & Peind(1)
    
    Dim LijnObj As AcadLine
    Set LijnObj = ThisDrawing.ModelSpace.AddLine(Pbegin, Peind)
    LijnObj.Layer = LaagNaam
    LijnObj.Update
End Sub



Public Sub SchrijfLogFile(Tekst As String)
    '--------------------------------------------------------------------------------------------
    ' LOG-FILE SCHRIJVEN NAAR HARDDISK (TXT-FILE)
    '--------------------------------------------------------------------------------------------

    Dim filenum As Integer
    Dim textline As String

    'Kill ("C:\Temp\WTH-logfile.txt")
    
    filenum = FreeFile
    Open "C:\Temp\WTH-logfile.txt" For Append As filenum
        Print #filenum, Tekst
    Close filenum
    
End Sub

Public Sub VerwijderenLogFile()
    '--------------------------------------------------------------------------------------------
    ' VERWIJDEREN VOORGAANDE LOGFILE
    '--------------------------------------------------------------------------------------------
    Dim sLogFile As String
    sLogFile = "C:\Temp\WTH-logfile.txt"
    If Dir(sLogFile) <> "" Then Kill (sLogFile)
End Sub

  
'LET OP: DIT IS AANGEPAST MET EXTRA UITBREIDING ObjectNiet 29 APRIL 2004 !!
Public Function ZoekElementHandleRondPunt(p As Variant, dCrossingSelectieGrootte As Double, Optional ObjectHandleNiet As String) As String
    On Error Resume Next
    
    'DEZE FUNCTIE BEPAALD EEN ELEMENT ROND EEN OPGEGEVEN PUNT.
    'DE GROOTTE VAN DE SELECTIECROSSING KAN WORDEN OPGEGEVEN, WAARBIJ
    'DE OPGEGEVEN GROOTTE ZOWEL DE LENGTE ALS BREEDTE VORMT VAN HET
    'ZOEK-GEBIED.
    
    '1 EN 5 AUG 2003 DOOR EBR
    
    'LET OP: INDIEN GEEN ELEMENT GEVONDEN WORDT, DAN GEEFT DE FUNCTIE
    'EEN LEGE STRING TERUG !
    
    ' AANROEPEN BIJVOORBEELD ALSVOLGT:
    
    'Me.Hide
    'Dim P As Variant
    'Dim sHandle as string
    'P = ThisDrawing.Utility.GetPoint(, "Selecteer punt")
    'sHandle =  ZoekElementHandleRondPunt(P, 0)
    'IF sHandle) = "" THEN
    '   msgbox "geen element gevonden"
    'else
    '   MsgBox "gevonden: " & sHandle
    'end if
    

    '--------------------------------------------------------------
    ' INSTELLEN SELECTIE-GROOTTE
    ' --------------------------------------------------------------
   
    If dCrossingSelectieGrootte = 0 Then dCrossingSelectieGrootte = 0.1
    dCrossingSelectieGrootte = dCrossingSelectieGrootte / 2

    '--------------------------------------------------------------
    ' AANMAKEN SELECTIESET OM EINDPUNT ARC (ZOEK LIJN)
    ' --------------------------------------------------------------
   
    
    'Aanmaken selectieset
    
    Dim p1(0 To 2) As Double
    Dim p2(0 To 2) As Double

    p1(0) = p(0) - dCrossingSelectieGrootte
    p1(1) = p(1) - dCrossingSelectieGrootte
    p1(2) = 0
    p2(0) = p(0) + dCrossingSelectieGrootte
    p2(1) = p(1) + dCrossingSelectieGrootte
    p2(2) = 0
    
    Dim ssetObj As AcadSelectionSet
    Set ssetObj = ThisDrawing.SelectionSets.Add("SSET")
    If Err Then
        ssetObj.Clear
        ssetObj.Delete
        End
    End If
    
    ssetObj.Select acSelectionSetCrossing, p1, p2
    
    ' --------------------------------------------------------------
    ' UITLEZEN SELECTIESET EN ELEMENT OPVRAGEN
    ' --------------------------------------------------------------
    
    Dim element As Object
    Dim t As Integer
    Dim Object As AcadEntity
    
    For Each element In ssetObj
        'element.Color = acGreen
        'element.Highlight True
        t = t + 1
        If element.handle <> ObjectHandleNiet Then Set Object = element
    Next element


    ssetObj.Clear
    ssetObj.Delete
    
    ' --------------------------------------------------------------
    ' CONTROLE
    ' --------------------------------------------------------------
    
    If t = 0 Then
        'MsgBox "Geen lijn gevonden.", vbExclamation, "let op"
    Else
        'MsgBox Object.handle
        ZoekElementHandleRondPunt = Object.handle
    End If
    
End Function


Public Sub ZoomInOpElement(element As AcadEntity, bHighlight As Boolean)
    
    Dim minExt As Variant
    Dim maxExt As Variant

    element.GetBoundingBox minExt, maxExt
    ZoomWindow minExt, maxExt
    ZoomScaled 0.9, acZoomScaledRelative
    
    If bHighlight = True Then element.Highlight (True)

End Sub

Function GetalIsDouble(sGetal As String, Optional sMelding As String) As Boolean
        'Ebr 14 juni 2004

        Dim dGetal As Double
        
        On Error Resume Next
        
        dGetal = sGetal
        If Err Or (dGetal <> Val(sGetal)) Then
            Err.Clear
            GetalIsDouble = False
            If sMelding <> "" Then MsgBox sMelding, vbExclamation, "Let op"
        Else
            GetalIsDouble = True
        End If

End Function

Attribute VB_Name = "M_0Algemeen_FindFile"
#If VBA7 Then
    Public Declare PtrSafe Function SearchPath Lib "kernel32" Alias "SearchPathA" _
        (ByVal lpPath As String, _
         ByVal lpFileName As String, _
         ByVal lpExtension As String, _
         ByVal nBufferLength As Long, _
         ByVal lpBuffer As String, _
         ByVal lpFilePart As String) As Long
#Else
    Public Declare Function SearchPath Lib "kernel32" Alias "SearchPathA" _
        (ByVal lpPath As String, _
         ByVal lpFileName As String, _
         ByVal lpExtension As String, _
         ByVal nBufferLength As Long, _
         ByVal lpBuffer As String, _
         ByVal lpFilePart As String) As Long
#End If

Public Const MAX_PATH As Long = 260

' Returns the full path to the file if found in the search path, otherwise "ERROR"
Public Function FindFile(sFileName As String, Optional sPath As String = vbNullString) As String
    Dim retVal As Long
    Dim lpBuffer As String * MAX_PATH

    retVal = SearchPath(sPath, sFileName, vbNullString, MAX_PATH, lpBuffer, vbNullString)
    If retVal > 0 Then
        FindFile = Left(lpBuffer, retVal)
    Else
        FindFile = "ERROR"
    End If
End Function

' Looks for a file in SupportPath, Application Path, then Project Folder
Public Function FindZoekpad(bestandnaam As String) As String
    Dim sBestandnaam As String
    Dim sZoekpad As String

    sBestandnaam = bestandnaam
    sZoekpad = FindFile(sBestandnaam, ThisDrawing.Application.Preferences.Files.SupportPath)

    If sZoekpad = "ERROR" Then
        If Dir(ThisDrawing.Application.Path & "\" & sBestandnaam) <> "" Then
            FindZoekpad = ThisDrawing.Application.Path & "\" & sBestandnaam
        ElseIf Dir(CurDir & "\" & sBestandnaam) <> "" Then
            FindZoekpad = CurDir & "\" & sBestandnaam
        Else
            FindZoekpad = "ERROR"
        End If
    Else
        FindZoekpad = sZoekpad
    End If
End Function

Attribute VB_Name = "M_0CfgFiles"
    Dim sCfgFile As String
    
''''
''''Sub ControleCfgFile()
''''
'''''------------------------------------------------------
'''''CONTROLEREN OF CFG-FILE AANWEZIG IS.
'''''------------------------------------------------------
''''
''''    sCfgFile = "C:\TEMP\Rollengten.cfg"
''''
''''    'CONTROLE OF FILE BESTAAT:
''''    Dim ControleDirectory As String
''''    Dim DirBesaat As String
''''    DirBesaat = Dir(ControleDirectory)
''''    If DirBesaat = "" Then
''''        MsgBox "Configuratie bestand '" & sCfgFile & "' niet gevonden", vbCritical, "Leidingleg-programma"
''''        End
''''    End If
''''End Sub

Sub LeesCfgFile()
    
'------------------------------------------------------
'LEZEN CONFIGURATIE-FILE MET ROLLENGTEN.
'------------------------------------------------------
    
''''    Call ControleCfgFile

    
    
    sCfgFile = FindZoekpad("Rollengten.cfg")
    
    'LEZEN CONFIGURATIE-FILE:
    Dim sLine As String
    Dim bSectieGevonden As Boolean
    
    Open sCfgFile For Input As #1
    Do While Not EOF(1)
            Line Input #1, sLine
            sLine = Trim(sLine)
            If Left$(sLine, 1) <> "'" And sLine <> "" Then
                 
                'UITLEZEN SECTIE-NAAM [HOH] EN VULLEN COMBOBOX
                If UCase(sLine) = "[HOH]" Then bSectieGevonden = True
                If Left$(sLine, 1) = "[" And UCase(sLine) <> "[HOH]" Then bSectieGevonden = False
                
                If bSectieGevonden = True And Left$(sLine, 1) <> "[" Then F_Main.ComboBox2.AddItem sLine
            
                'UITLEZEN SECTIE-NAMEN MET DE ROLTYPEN, NIEUWE SECTIES KUNNEN WORDEN TOEGEVOEGD
                If Left$(sLine, 1) = "[" And Right$(sLine, 1) = "]" Then
                    If UCase(sLine) <> "[HOH]" Then
                            sLine = Right$(sLine, Len(sLine) - 1)
                            sLine = Left$(sLine, Len(sLine) - 1)
                            F_Main.ComboBox3.AddItem sLine
                    End If
                End If
               
                
            End If
    Loop
    Close #1

End Sub


Sub ChangeRollengten()

    
    F_InvoerRollengte.ComboBox1.Clear
    
    'Call ControleCfgFile
    
    sCfgFile = FindZoekpad("Rollengten.cfg")
    
    'LEZEN CONFIGURATIE-FILE:
    Dim sLine As String
    Open sCfgFile For Input As #1
    Dim bSectieGevonden As Boolean
    
    Do While Not EOF(1)
            Line Input #1, sLine
            sLine = Trim(sLine)
            If Left$(sLine, 1) <> "'" And sLine <> "" Then
            
                'CONTROLE OF JUISTE SECTIE GELEZEN WORDT
                If Left$(sLine, 1) = "[" Then
                    If UCase(sLine) = "[" & UCase(F_Main.ComboBox3.Text) & "]" Then
                        bSectieGevonden = True
                    Else
                        bSectieGevonden = False
                    End If
                End If
                
                'INDIEN JUISTE SECTIE,DAN COMBO ROLLENGTEN INVULLEN
                If bSectieGevonden = True And Left$(sLine, 1) <> "[" Then F_InvoerRollengte.ComboBox1.AddItem sLine
                'F_Main.ListBox5.AddItem sLine
                
            End If
    Loop
    Close #1
End Sub

Attribute VB_Name = "M_0SaveGetSettings"
Sub SaveSettings()
    SaveSetting "Leidinglegprogramma", "Startup", "HOHAfstand", F_Main.ComboBox2.Value
    SaveSetting "Leidinglegprogramma", "Startup", "LeidingType", F_Main.ComboBox3.Value
    SaveSetting "Leidinglegprogramma", "Startup", "Snit", F_Main.TextBox1.Text
    SaveSetting "Leidinglegprogramma", "Startup", "OpgevenAantalLeid", F_Main.CheckBox10.Value
    
    

End Sub


Sub GetSettings()
    F_Main.ComboBox2.Text = GetSetting("Leidinglegprogramma", "Startup", "HOHAfstand", "")
    F_Main.ComboBox3.Text = GetSetting("Leidinglegprogramma", "Startup", "LeidingType", "")
    F_Main.TextBox1.Text = GetSetting("Leidinglegprogramma", "Startup", "Snit", "0")
    F_Main.CheckBox10.Value = GetSetting("Leidinglegprogramma", "Startup", "OpgevenAantalLeid", False)
       
    
    If Trim(F_Main.TextBox1.Text) = "" Then F_Main.TextBox1.Text = 0
End Sub

Attribute VB_Name = "M_0Start"


Public Sub Start()
    F_LengteMonitor.Image1.Visible = False
    F_LengteMonitor.Image2.Visible = True
    F_Main.show
End Sub

Public Sub Start1()
    Call M_6PlaatsenSlingers.OpvragenHOH
End Sub

Public Sub Start2()
    Call F_Main.OpschuivenLegpatroon
End Sub

Public Sub Start3()
    Call M_0SaveGetSettings.SaveSettings
    Call M_5BerekenLengteInLayers.BerekenLengteInColors
End Sub

Attribute VB_Name = "M_1Hatch"
Public Sub PlaatsenHatch()


' -----------------------------------------------------------------------------------
' CONTROLE OPGEGEVEN HOH
' -----------------------------------------------------------------------------------

    Dim iHOH As Integer
    On Error Resume Next
    iHOH = F_Main.ComboBox2.Text
    
    If Err Then
        Err.Clear
        MsgBox "Geen juiste HOH-afstand opgegeven.", vbCritical, "Let op"
        End
    End If
    
'    Dim antw As String
'    If iHOH > 35 Then
'        antw = MsgBox("HOH-afstand is groter dan 35 cm. Toch doorgaan ?", vbYesNo + vbQuestion, "leidingleg programma")
'        If antw = vbNo Then End
'    End If

' -----------------------------------------------------------------------------------
' HIDE FORM
' -----------------------------------------------------------------------------------
    
    F_Main.Hide
    
' -----------------------------------------------------------------------------------
' JUISTE LAAG AKTIEF MAKEN
' -----------------------------------------------------------------------------------
    ' voor 27 mei 2003 was kleur 5 (blue)
    AanmakenLaag "Legplan", 2, True
    
    
' -----------------------------------------------------------------------------------
' LAAG BOUWKUNDIG UITZETTEN nieuw 7 april 2003
' -----------------------------------------------------------------------------------

    Dim LaagBouwkundig As AcadLayer
    Dim Laag As AcadLayer
    Dim LaagBouwkundigBestaat As Boolean
    For Each Laag In ThisDrawing.Layers
        If UCase(Laag.Name) = "BOUWKUNDIG" Then Set LaagBouwkundig = Laag: LaagBouwkundigBestaat = True
    Next Laag
    
    Dim sAntw As String
    If LaagBouwkundigBestaat = False Then
        sAntw = MsgBox("Er is geen laag 'Bouwkundig' aanwezig." _
        & Chr(10) & Chr(13) & "Selecteer de bouwkundige laag.", vbYesNo + vbExclamation, "Geen laag 'bouwkundig'")
        If sAntw = vbYes Then Call HernoemLaag
        
        ' INDIEN LAAG IS AANGEMAAKT DAN BEVRIEZEN
        For Each Laag In ThisDrawing.Layers
            If UCase(Laag.Name) = "BOUWKUNDIG" Then
                Set LaagBouwkundig = Laag
                LaagBouwkundig.Freeze = True
            End If
        Next Laag
        
    Else
        'If LaagBouwkundig.Lock = True Then LaagBouwkundig.Lock = False
        LaagBouwkundig.Freeze = True
    End If
    

' ___________________________________________________________________________________
' Tellen hoeveel buitengrens-lijnen en hoeveel obstakels er zijn
' ___________________________________________________________________________________

    Dim OuterlObj As Object   ' hier AcadEntity niet gebruiken
    Dim RetObj As Object
    Dim iFoutSelectieTeller1 As Integer
    
    
    
    ' 27 MEI 2003 SELECTIE AANGEPAST
Opnieuw1:
    
    ThisDrawing.Utility.GetEntity RetObj, p, "Selecteer een ruimte-polyline"
    
    If iFoutSelectieTeller1 > 0 Then End
    
    If Err <> 0 Then
        If iFoutSelectieTeller1 < 1 Then MsgBox "Verkeerde selectie", vbCritical
        iFoutSelectieTeller1 = iFoutSelectieTeller1 + 1
        Err.Clear
        GoTo Opnieuw1
    Else
        RetObj.Highlight (True)
    End If
            
    If RetObj.EntityName = "AcDbPolyline" Then
        Set OuterlObj = RetObj
    Else
        If iFoutSelectieTeller1 < 1 Then MsgBox "Geen polyline geselecteerd", vbCritical
        iFoutSelectieTeller1 = iFoutSelectieTeller1 + 1
        GoTo Opnieuw1
        'End
    End If

    ''''plineObj.Closed = True
    
' ___________________________________________________________________________________
' Geselecteerde Omtrek-polyline in laag "LegplanOmtrek"
' ___________________________________________________________________________________
    
    Call AanmakenLaag("Legplanomtrek", 6, False)
    RetObj.Layer = "Legplanomtrek"
            

' -----------------------------------------------------------------------------------
' Aangeven hoek van hatch
' -----------------------------------------------------------------------------------


    F_Main.Hide
    
    'P1: DIT IS OOK HET BEGINPUNT VOOR HET UCS.
    Dim p1 As Variant
    On Error Resume Next
    p1 = ThisDrawing.Utility.GetPoint(, "Geef de zijde aan van de eerste leiding")
    If Err Then
        Err.Clear
        End
    End If
    
    Dim p2 As Variant
    On Error Resume Next
    p2 = ThisDrawing.Utility.GetPoint(p1, "Geef de leidingrichting aan.")
    If Err Then
        Err.Clear
        End
    End If
    
    
    
    Dim retAngle As Double
    Dim retAngleOrgineel As Double
    
    retAngle = ThisDrawing.Utility.AngleFromXAxis(p1, p2)
    retAngleOrgineel = retAngle
    retAngle = retAngle - (3.14159265358979 / 4)
    
    'testdoeleinden: Dit is een hoek van 0 graden (voor de 45 graden hatch):
    'retAngle = 0 - (3.14159265358979 / 4)
    
    
' -----------------------------------------------------------------------------------
' ucs verplaatsen (iets lager of hoger)
' -----------------------------------------------------------------------------------
    
    
    'BEREKENEN POLAIRPOINT
    

    Dim Ppolair As Variant
    ' Ppolair = ThisDrawing.Utility.PolarPoint(P1, 1.5707963, 6.35)     'voor hoeken van 0 graden
    Ppolair = ThisDrawing.Utility.PolarPoint(p1, retAngleOrgineel + 1.5707963, F_Main.ComboBox2 / 2)     'halve hoh
    'Dim PUNTOBJ As AcadPoint
    'Set PUNTOBJ = ThisDrawing.ModelSpace.AddPoint(Ppolair)
   
   
   
   
    'VERPLAATSEN UCS
   
    Dim viewportObj As AcadViewport
    Set viewportObj = ThisDrawing.ActiveViewport
    
    ' Create a new UCS with origin 200, 200, 0
    Dim UcsObj As AcadUCS
    Dim origin(0 To 2) As Double            'positie
    Dim xAxisPoint(0 To 2) As Double        'x-richting
    Dim yAxisPoint(0 To 2) As Double        'y-richting
    
    origin(0) = Ppolair(0): origin(1) = Ppolair(1): origin(2) = 0
    xAxisPoint(0) = Ppolair(0) + 100: xAxisPoint(1) = Ppolair(1): xAxisPoint(2) = 0
    yAxisPoint(0) = Ppolair(0): yAxisPoint(1) = Ppolair(1) + 100: yAxisPoint(2) = 0
    
    Set UcsObj = ThisDrawing.UserCoordinateSystems.Add(origin, xAxisPoint, yAxisPoint, "UCS1")
    ThisDrawing.ActiveUCS = UcsObj
    viewportObj.UCSIconOn = True
    viewportObj.UCSIconAtOrigin = True
    ThisDrawing.ActiveViewport = viewportObj
    
    'Sysvar: UCSORG geeft aan waar het UCS zich bevindt (read only)
    'MsgBox "The origin of the UCS is: " & UcsObj.origin(0) & ", " & UcsObj.origin(1) & ", " & UcsObj.origin(2), , "Origin Example"
    
   
'----------------------------------------------------------------------------------
'INZOOMEN IN RUIMTEPOLYLINE
'----------------------------------------------------------------------------------
    
    Dim minExt As Variant
    Dim maxExt As Variant

    RetObj.GetBoundingBox minExt, maxExt
    ZoomWindow minExt, maxExt
    
    
' -----------------------------------------------------------------------------------
' Hatch-object aanmaken, maar nog niet vullen (incl schaal en hoek)
' -----------------------------------------------------------------------------------


    Dim HoHafstand As Double
    Dim HatchSchaal As Double
    
    HoHafstand = F_Main.ComboBox2.Text                ' INVOER H-op-H afstand
    'HOHafstand = 10
    HatchSchaal = HoHafstand * 0.3149606299
            
    
    Dim HatchObj As Object  'niet gebruiken: AcadHatch
    Dim patternName As String
    Dim PatternType As Long
    Dim bAssociativity As Boolean
        
    ' Define the hatch
    patternName = "ANSI31"
    PatternType = 0

    bAssociativity = True
    Set HatchObj = ThisDrawing.ModelSpace.AddHatch(PatternType, patternName, bAssociativity)
    
    
    HatchObj.PatternScale = HatchSchaal            ' declareren as double
    
    HatchObj.HatchStyle = acHatchStyleOuter
    

    
    
'''    Dim p1 As Variant
'''    Dim ArceerHoek As Double
'''
'''
'''    ''HoekInGraden = ComboBox3.Text
'''    HoekInGraden = 0
'''
'''    ' Hoek standaard al -45 graden verdraaien om deze horizontaal te zetten
'''    HoekInRad = ThisDrawing.Utility.AngleToReal(HoekInGraden - 45, acDegrees)
'''    HatchObj.PatternAngle = HoekInRad

    HatchObj.PatternAngle = retAngle


    
   
    
   
' ___________________________________________________________________________________
' OFFSETTEN POLYLINE
' ___________________________________________________________________________________
'    Dim offsetObj As Variant
'    offsetObj = retObj.Offset(HoHafstand)
'
'    offsetObj(0).Color = 53
'
'    'CONTROLEREN OF OFFSET RICHTING JUIST IS MIDDELS BOUNDINGBOX EN BEREKENEN OPPERVL.
'    'IS DIT NIET HET GEVAL DAN OFFSET-OBJ VERWIJDEREN EN OPNIEUW OFFSETTEN
'    'IN DE TEGENGESTELDE RICHTING.
'
'    Dim minExt As Variant
'    Dim maxExt As Variant
'    Dim Lengte As Double
'    Dim hoogte As Double
'    Dim Oppervlakte1 As Double
'    Dim Oppervlakte2 As Double
'
'    retObj.GetBoundingBox minExt, maxExt
'    Lengte = maxExt(0) - minExt(0)
'    hoogte = maxExt(1) - minExt(1)
'    Oppervlakte1 = Lengte * hoogte
'
'    offsetObj(0).GetBoundingBox minExt, maxExt
'    Lengte = maxExt(0) - minExt(0)
'    hoogte = maxExt(1) - minExt(1)
'    Oppervlakte2 = Lengte * hoogte
'
'    'INDIEN DE OFFSET RICHTING VERKEERD IS (NAAR BUITEN I.P.V. NAAR BINNEN).
'    If Oppervlakte2 > Oppervlakte1 Then
'        offsetObj(0).Erase
'        offsetObj = retObj.Offset(-HoHafstand / 2)
'        offsetObj(0).Color = 53
'    End If
'
'    Set OuterlObj = offsetObj(0)

'---------------------------------------------
'nieuw, vervangen door:

    Set OuterlObj = RetObj
    
' ___________________________________________________________________________________
' Outerloop aanmaken met een (1) gefilterde buitengrens-lijn
' ___________________________________________________________________________________

    'Dim outerloop(0 To 0) As Object
    Dim outerloop(0 To 0) As Object ' geen AcadEntity gebruiken
    Set outerloop(0) = OuterlObj
        
    On Error Resume Next
    HatchObj.AppendOuterLoop (outerloop)
    If Err Then
        Err.Clear
        MsgBox "De hulpoffset-lijn (magenta outerloop) is niet aangegeven. ", vbCritical, "(errcode 3)"
        'OuterlObj.Erase        27 mei 2004 uitgezet !
        OuterlObj.Highlight (True)
        
        'NIEUW 27 MEI 2004: UCS WEER TERUGPLAATSEN !!!
         origin(0) = 0: origin(1) = 0: origin(2) = 0
        xAxisPoint(0) = 100:   xAxisPoint(1) = 0:       xAxisPoint(2) = 0
        yAxisPoint(0) = 0:     yAxisPoint(1) = 100:     yAxisPoint(2) = 0

        Set UcsObj = ThisDrawing.UserCoordinateSystems.Add(origin, xAxisPoint, yAxisPoint, "UCS1")

        ThisDrawing.ActiveUCS = UcsObj
        viewportObj.UCSIconOn = True
        viewportObj.UCSIconAtOrigin = True
        ThisDrawing.ActiveViewport = viewportObj

        Set UcsObj = Nothing
        
        'Exit Sub
        End
    End If
    
' ___________________________________________________________________________________
' Innerloop aanmaken met een (5) obstakel
' ___________________________________________________________________________________

'Dim ElementTeller As Integer
'Dim ObstakelTeller As Integer
'
'For ElementTeller = 0 To ThisDrawing.ModelSpace.Count - 1
'    If ThisDrawing.ModelSpace.Item(ElementTeller).Color = acCyan Then ' **acYellow
'        ObstakelTeller = ObstakelTeller + 1
'
'        Select Case ObstakelTeller
'        Case 1
'            Dim innerLoop1(0) As Object                     ' of (0 to 0) of (0) 0f ()
'            Set innerLoop1(0) = ThisDrawing.ModelSpace.Item(ElementTeller)
'            HatchObj.AppendInnerLoop (innerLoop1)
'        Case 2
'            Dim innerLoop2(0) As Object
'            Set innerLoop2(0) = ThisDrawing.ModelSpace.Item(ElementTeller)
'            HatchObj.AppendInnerLoop (innerLoop2)
'        Case 3
'            Dim innerLoop3(0) As Object
'            Set innerLoop3(0) = ThisDrawing.ModelSpace.Item(ElementTeller)
'            HatchObj.AppendInnerLoop (innerLoop3)
'        Case 4
'            Dim innerLoop4(0) As Object
'            Set innerLoop4(0) = ThisDrawing.ModelSpace.Item(ElementTeller)
'            HatchObj.AppendInnerLoop (innerLoop4)
'        Case 5
'            Dim innerLoop5(0) As Object
'            Set innerLoop5(0) = ThisDrawing.ModelSpace.Item(ElementTeller)
'            HatchObj.AppendInnerLoop (innerLoop5)
'        End Select
'    End If
'Next ElementTeller




''??If ObstakelTeller = 0 Then MsgBox "Er zijn geen obstakels gevonden", vbInformation, "Aantal obstakels"
''??If ObstakelTeller = 1 Then MsgBox "Er is 1 obstakel gevonden", vbInformation, "Aantal obstakels"
''??If ObstakelTeller > 1 And ObstakelTeller < 6 Then MsgBox "Er zijn " & ObstakelTeller & " obstakels gevonden", vbInformation, "Aantal obstakels"
''??If ObstakelTeller > 5 Then MsgBox "Let op er zijn " & ObstakelTeller & " obstakels gevonden", vbCritical, "Meer dan 5 obstakels"

' --------------------------------------------------------------------------------
' NIEUW: INNERLOOP AANGEVEN DOOR DE GEBRUIKER (5 OBSTAKELS SELECTEREN)
' --------------------------------------------------------------------------------


    Dim returnString As String
    returnString = ThisDrawing.Utility.GetString(False, "Zijn er obstakels ?: Ja <Nee>: ")
    'MsgBox returnString, vbExclamation
    If UCase(Left$(returnString, 1)) = "N" Or returnString = "" Then GoTo PlaatsenHatch
    
    
    'UILEZEN SELECTIESET:
    

    Dim ssetObj As AcadSelectionSet
    Dim bStoppen As Boolean
    
opnieuw:
    bStoppen = False
    Set ssetObj = ThisDrawing.SelectionSets.Add("SSET1")
    
    ssetObj.SelectOnScreen
    
    If Err Then
        'enter is doorgaan
        Err.Clear
    End If
    
    Dim element As Object
    Dim ObstakelTeller As Integer
    
    
    'CONTROLE OF ER POLYLINES GESELECTEERD ZIJN:
    For Each element In ssetObj
        If element.EntityName <> "AcDbPolyline" Then
            element.Highlight = True
            bStoppen = True
        End If
    Next element
    
    If bStoppen = True Then
        MsgBox "Geselecteerde element is geen polyline.", vbCritical, "Let op"
        ssetObj.Clear
        ssetObj.Delete
        GoTo opnieuw
    End If
        
    
    
    'UITLEZEN SLECTIESET EN VAN DE POLYLINES HATCH-ISLANDS MAKEN:
    For Each element In ssetObj
    
        If element.EntityName = "AcDbPolyline" Then
        
            element.Layer = "Legplanomtrek"
    
            ObstakelTeller = ObstakelTeller + 1
        
            Select Case ObstakelTeller
            Case 1
                Dim innerLoop1(0) As Object                     ' of (0 to 0) of (0) 0f ()
                Set innerLoop1(0) = element
                HatchObj.AppendInnerLoop (innerLoop1)
            Case 2
                Dim innerLoop2(0) As Object
                Set innerLoop2(0) = element
                HatchObj.AppendInnerLoop (innerLoop2)
            Case 3
                Dim innerLoop3(0) As Object
                Set innerLoop3(0) = element
                HatchObj.AppendInnerLoop (innerLoop3)
            Case 4
                Dim innerLoop4(0) As Object
                Set innerLoop4(0) = element
                HatchObj.AppendInnerLoop (innerLoop4)
            Case 5
                Dim innerLoop5(0) As Object
                Set innerLoop5(0) = element
                HatchObj.AppendInnerLoop (innerLoop5)
            Case Else
                MsgBox "Er mogen maximaal 5 obstakels worden geselecteerd", vbCritical, "Let op"
                bStoppen = True
            End Select
            
        End If
    Next element
           
            
    
    
    ssetObj.Clear
    ssetObj.Delete
    
    If bStoppen = True Then End
        
        

    
    
    


''''''' ___________________________________________________________________________________
''''''' een innerloops in een innerloop toevoegen (niet nodig !!)
''''''' ___________________________________________________________________________________
''''''
''''''    Dim loopobj(0 To 0) As Object
''''''    Set loopobj(0) = ThisDrawing.ModelSpace.Item(2)
''''''
''''''
''''''    Dim ObstTeller As Integer
''''''    For ObstTeller = 1 To 4
''''''        Set loopobj(0) = ThisDrawing.ModelSpace.Item(ObstTeller)
''''''        HatchObj.InsertLoopAt HatchObj.NumberOfLoops, acHatchLoopTypeDefault, loopobj
''''''    Next ObstTeller
''''''
''''''    'hatchObj.InsertLoopAt hatchObj.NumberOfLoops, acHatchLoopTypeDefault, loopobj

' ___________________________________________________________________________________
' Arcering afbeelden
' ___________________________________________________________________________________



PlaatsenHatch:

    'MsgBox "Berekenen voorlopig legpatroon.", vbExclamation

    'HatchObj.AssociativeHatch = False
    HatchObj.Evaluate
    HatchObj.Color = acByLayer
    HatchObj.Layer = "Legplan"
    HatchObj.Update
    'ThisDrawing.Activate
    
   
    '-----------------------------------------

'    'hulppolyline verwijderen
'    Dim HulpPolyLine
'    For Each HulpPolyLine In ThisDrawing.ModelSpace
'        If HulpPolyLine.Color = 53 Then element.HulpPolyLine
'    Next HulpPolyLine
'

''    If Err Then
''        Err.Clear
''        MsgBox "Controleer het legplatroon (object-type)", vbInformation, "Let op"
''    End If

    UcsObj.Delete
    
    'HatchObj.Explode   'DIT IS VOOR ARCERINGEN NIET MOGELIJK (R2002 EN EERDERE VERSIES) !
    On Error Resume Next
    
    'ThisDrawing.SendCommand ("erase" & vbCr & "l" & vbCr & vbCr) 'weggehaald, polyline wordt niet meer getekend.
    ThisDrawing.SendCommand ("explode" & vbCr & "l" & vbCr & vbCr)
    'ThisDrawing.SendCommand ("USC" & vbCr & "W" & vbCr)
    ThisDrawing.Activate

'    ThisDrawing.Regen True

    'MsgBox "VOOR EXPLODE"
    'ThisDrawing.SendCommand ("(COMMAND ""_-VBARUN"" ""PART2"")" & vbCr)
    'ThisDrawing.SendCommand ("_-VBARUN " & "PART2 ")
      
      
    '----------------------------------------------------------------------------------
    'BEPALEN OF ER OBSTAKELS ZIJN, DIT EVEN UITGEZET.
    '----------------------------------------------------------------------------------
    '** UITGEZET OP 10 DECEMBER 2002
    Application.RunMacro "part2"
    
    'ThisDrawing.Regen (True)
    'MsgBox "NA SENDCOMMAND AANROEP PART2"
    
    
    '----------------------------------------------------------------------------------
    'UCS WEER TERUG PLAATSEN IN WORLD
    '----------------------------------------------------------------------------------
    
    origin(0) = 0: origin(1) = 0: origin(2) = 0
    xAxisPoint(0) = 100:   xAxisPoint(1) = 0:       xAxisPoint(2) = 0
    yAxisPoint(0) = 0:     yAxisPoint(1) = 100:     yAxisPoint(2) = 0

    Set UcsObj = ThisDrawing.UserCoordinateSystems.Add(origin, xAxisPoint, yAxisPoint, "UCS1")

    ThisDrawing.ActiveUCS = UcsObj
    viewportObj.UCSIconOn = True
    viewportObj.UCSIconAtOrigin = True
    ThisDrawing.ActiveViewport = viewportObj

    Set UcsObj = Nothing



    '----------------------------------------------------------------------------------
    'OPNIEUW INZOOMEN IN RUIMTEPOLYLINE OMDAT UCS WEER TERUGGEZET IS ?
    '----------------------------------------------------------------------------------
        
'    Dim minExt As Variant
'    Dim maxExt As Variant

    RetObj.GetBoundingBox minExt, maxExt
    ZoomWindow minExt, maxExt
    
    
    
    ' -----------------------------------------------------------------------------------
    ' LAAG BOUWKUNDIG WEER AANZETTEN nieuw 7 april 2003
    ' -----------------------------------------------------------------------------------

    If LaagBouwkundigBestaat = True Then LaagBouwkundig.Freeze = False


    
    
   
    

End Sub


Sub PART2()
    Call BepaalObstakels(False)
End Sub



Sub HernoemLaag()

    ' aanvulling 27 jan 2004
    Dim ReturnObj1 As AcadObject
    Dim p1 As Variant

    ThisDrawing.Utility.GetEntity ReturnObj1, p1, "(Laag hernoemen > Selecteer een bouwkundig element:"
    
    If Err Then
        Err.Clear
        Exit Sub
    End If
    
    Dim LaagObj As AcadLayer
    Set LaagObj = ThisDrawing.Layers.Item(ReturnObj1.Layer)
    LaagObj.Name = "BOUWKUNDIG"
    LaagObj.Color = 8
    
    If Err Then
        Err.Clear
        MsgBox "Laag " & ReturnObj1.Layer & " kan niet worden hernoemd."
        Exit Sub
    End If
    


End Sub

Attribute VB_Name = "M_1InkortenLijnen"


Public Sub AlleLijnenInkorten(ItemNrVanEersteElement)

'''GEWIJZIGD OP 24 FEB 2003

    'inkorten alle lijnen in laag "Legplan"

'    Dim Element As Object
'    For Each Element In ThisDrawing.ModelSpace
'        If Element.EntityName = "AcDbLine" Then
'            If Element.Layer = "Legplan" Then
'                Call M_InkortenLijnen.InkortenLijnen(Element, F_Main.ComboBox2)
'            End If
'        End If
'    Next Element

    Dim element As Object
    Dim t As Double
    
    For t = ThisDrawing.ModelSpace.Count - 1 To 0 Step -1
    
        If t > ItemNrVanEersteElement - 1 Then
    
            Set element = ThisDrawing.ModelSpace.Item(t)
            If element.EntityName = "AcDbLine" Then
                If element.Layer = "Legplan" Then
                    Call M_1InkortenLijnen.InkortenLijnen(element, F_Main.ComboBox2)
                End If
            End If
        End If
    Next t
    
End Sub
Sub InkortenLijnen(LijnObj As AcadLine, HoH As Double)

    'Principe:
    'Hoek opvragen van lijn, lijn op 0 graden draaien en
    'begin en eindpunt (x-coordinaten) inkorten met halve hart-op-hart afstand
    'daarna lijn weer goed terugdraaien om het oorspronkelijke draaipunt Pdraai.
    
    If LijnObj.Length < (2 * HoH) Then Exit Sub

    Dim Pbegin As Variant
    Dim Peind As Variant
    Dim HOEK As Double
    Dim Pdraai As Variant
    
    Pdraai = LijnObj.StartPoint
    HOEK = LijnObj.Angle
    'MsgBox Hoek
    
    LijnObj.Rotate Pdraai, -HOEK
    
    Pbegin = LijnObj.StartPoint
    Peind = LijnObj.EndPoint
        
'    If Pbegin(0) < Peind(0) Then
'        Pbegin(0) = Pbegin(0) + (HOH / 2)
'        Peind(0) = Peind(0) - (HOH / 2)
'    End If
'    If Pbegin(0) > Peind(0) Then
'        MsgBox "Anders"
'        Pbegin(0) = Pbegin(0) - (HOH / 2)
'        Peind(0) = Peind(0) + (HOH / 2)
'    End If

    Pbegin(0) = Pbegin(0) + (HoH)
    Peind(0) = Peind(0) - (HoH)
    
     
    LijnObj.StartPoint = Pbegin
    LijnObj.EndPoint = Peind
    
    LijnObj.Rotate Pdraai, HOEK

End Sub

Attribute VB_Name = "M_2BepaalObstakels"
Public Sub BepaalObstakels(Stoppen As Boolean)

F_Main.ListBox1.Clear

Dim element As Object
Dim RotHoek As Double
Dim Pdraai(0 To 2) As Double
Dim LijnInJuistelaagGevonden As Boolean

Pdraai(0) = 0
Pdraai(1) = 0
Pdraai(2) = 0

'--------------------------------------------------------------------------
'BEPALEN ROTATIEHOEK
'---------------------------------------------------------------------------

For Each element In ThisDrawing.ModelSpace
    If element.EntityName = "AcDbLine" And element.Layer = "Legplan" Then
        RotHoek = element.Angle
        'MsgBox RotHoek
        LijnInJuistelaagGevonden = True
        Exit For
    End If
Next element

If LijnInJuistelaagGevonden = False Then
    MsgBox "Er zijn geen lijnen in laag 'Legplan' gevonden.", vbExclamation, "Obstakels kunnen niet worden bepaald"
    End
End If

'--------------------------------------------------------------------------
'ALLE LIJNEN RECHT PLAATSEN (HOEK 0 GRADEN) + OPSLAAN HANDLE IN LISTBOX
'---------------------------------------------------------------------------

For Each element In ThisDrawing.ModelSpace
    If element.EntityName = "AcDbLine" And element.Layer = "Legplan" Then
        F_Main.ListBox1.AddItem element.handle
        element.Rotate Pdraai, -RotHoek
    End If
    
Next element


'--------------------------------------------------------------------------
'BEPALEN OF ER LIJNEN OP DEZELFDE X-COORDINAAT LIGGEN (DUS NAAST ELKAAR)
'---------------------------------------------------------------------------
Dim lijn1 As Object
Dim lijn2 As Object
Dim lijn3 As Object

Dim StartpuntLijn1 As Variant
Dim StartpuntLijn2 As Variant
Dim StartpuntLijn3 As Variant
            
Dim ListTel As Integer
For ListTel = 0 To F_Main.ListBox1.ListCount - 3
                 
                'MsgBox ListBox1.List(2)
            
                Set lijn1 = ThisDrawing.HandleToObject(F_Main.ListBox1.List(ListTel))
                Set lijn2 = ThisDrawing.HandleToObject(F_Main.ListBox1.List(ListTel + 1))
                Set lijn3 = ThisDrawing.HandleToObject(F_Main.ListBox1.List(ListTel + 2))
                
                StartpuntLijn1 = lijn1.StartPoint
                StartpuntLijn2 = lijn2.StartPoint
                StartpuntLijn3 = lijn3.StartPoint
                
                'nieuw op 14 jan 2003:
                'lijn1.Color = acBlue
                
                ' *** 27 mei 2003 kleur aangepast in geel
                lijn1.Color = acYellow
                
                
                  
                'CONTROLEREN OF LIJNEN NAAST ELKAAR LIGGEN OP ZELFDE Y-COORDINAAT
                '(GEBRUIK VAN FORMAT OM ENIGE AFWIJKING IN Y-RICHTING TOCH GOED OP TE VANGEN):
                
                If Round(StartpuntLijn1(1), 0) = Round(StartpuntLijn2(1), 0) = Round(StartpuntLijn3(1), 0) Then
                  
                    'lijn1.Color = acMagenta
                   'lijn2.Color = acYellow
                    'lijn3.Color = acGreen
                   'ListTel = ListTel + 2
                ElseIf Round(StartpuntLijn1(1), 0) = Round(StartpuntLijn2(1), 0) Then
 
                    '*** ORIGINEEL VOOR 27 MEI 2003
'                    lijn1.Color = acYellow
'                    lijn2.Color = acGreen
'                    lijn3.Color = acRed  'DEZE UITVINKEN !?
                    
                    lijn1.Color = 21
                    lijn2.Color = 171
                    lijn3.Color = acRed  'DEZE UITVINKEN !?
                    
                    ListTel = ListTel + 1
                End If
       
Next ListTel



'--------------------------------------------------------------------------
'TERUGDRAAIEN LIJNEN MET DE ROTATIEHOEK
'---------------------------------------------------------------------------


For Each element In ThisDrawing.ModelSpace
    If element.EntityName = "AcDbLine" And element.Layer = "Legplan" Then
        element.Rotate Pdraai, RotHoek
    End If

Next element

If Stoppen = True Then End


End Sub

' ORGINEEL PRINCIPE

'''''Public Sub BepaalObstakels()
'''''
'''''Dim lijn1 As Object
'''''Dim lijn2 As Object
'''''Dim lijn3 As Object
'''''
'''''Dim StartpuntLijn1 As Variant
'''''Dim StartpuntLijn2 As Variant
'''''Dim StartpuntLijn3 As Variant
'''''
'''''Dim teller As Integer
'''''For teller = 0 To ThisDrawing.ModelSpace.Count - 3          '2 lijnen dan -2
'''''
'''''
'''''
'''''       If ThisDrawing.ModelSpace.Item(teller).Layer = "Legplan" Then Set lijn1 = ThisDrawing.ModelSpace.Item(teller)
'''''       If ThisDrawing.ModelSpace.Item(teller + 1).Layer = "Legplan" Then Set lijn2 = ThisDrawing.ModelSpace.Item(teller + 1)
'''''       If ThisDrawing.ModelSpace.Item(teller + 2).Layer = "Legplan" Then Set lijn3 = ThisDrawing.ModelSpace.Item(teller + 2)
'''''
'''''       StartpuntLijn1 = lijn1.StartPoint
'''''       StartpuntLijn2 = lijn2.StartPoint
'''''       StartpuntLijn3 = lijn3.StartPoint
'''''
'''''       'CONTROLEREN OF LIJNEN NAAST ELKAAR LIGGEN OP ZELFDE Y-COORDINAAT
'''''
'''''       If StartpuntLijn1(1) = StartpuntLijn2(1) = StartpuntLijn3(1) Then
'''''            lijn1.Color = acRed
'''''            lijn2.Color = acBlue
'''''            lijn3.Color = acGreen
'''''            teller = teller + 2
'''''       ElseIf StartpuntLijn1(1) = StartpuntLijn2(1) Then
'''''            lijn1.Color = acBlue
'''''            lijn2.Color = acGreen
'''''            'lijn3.Color = acRed
'''''            teller = teller + 1
'''''       End If
'''''
'''''Next teller
'''''
'''''
'''''End Sub

Attribute VB_Name = "M_3B_OffsetPoly"
Sub OffsetPoly()
    
    '-----------------------------------------------------------------------
    ' DEZE ROUTINE OFFSET DE GESELECTEERDE AANVOER-POLYLINE MET AFSTAND HOH
    '-----------------------------------------------------------------------
    
    'GEHEEL NIEUW OP 21 MAART 2003 EBR
    'TEN 15:09 TO 16:10= TOTAAL 1 UUR


    F_Main.Hide
    
    '-----------------------------------------------------------------------
    ' CONTROLE HOH
    '-----------------------------------------------------------------------
    
    Dim dHOH As Double
    
    On Error Resume Next
    dHOH = F_Main.ComboBox2.Text
    
    If Err Then
        Err.Clear
        MsgBox "De ingevoerde HOH-afstand is niet juist.", vbCritical, "Let op"
        Exit Sub
        F_Main.show
    End If
    
    '-----------------------------------------------------------------------
    ' LAAG "LEGPLANOMTREK" UITZETTEN.
    '-----------------------------------------------------------------------
        
    ThisDrawing.Layers.Item("Legplanomtrek").LayerOn = False
    If Err Then
        Err.Clear
        'MsgBox "Laag legplanomtrek kan niet worden uitgezet", vbCritical, "WTH-offset"
    End If
    
    
    '-----------------------------------------------------------------------
    ' OSNAP UITZETTEN EN ONTHOUDEN (LUKT NIET)
    '-----------------------------------------------------------------------
    
'    Dim iOsmode 'As Integer
'    iOsmode = ThisDrawing.GetVariable("OSMODE")
'    MsgBox iOsmode
'    ThisDrawing.SetVariable "OSMODE", 0
    
    '-----------------------------------------------------------------------
    ' SELECTEER DE AANVOER-POLYLINE
    '-----------------------------------------------------------------------

    
    Dim p1 As Variant
    Dim RetObj As AcadEntity
    
    Dim iFoutSelectieTeller As Integer
    
              
Opnieuw1:
    
    If iFoutSelectieTeller > 1 Then End
    
    ThisDrawing.Utility.GetEntity RetObj, p1, "Selecteer de aanvoer-polyline."
    'RetObj.Highlight (True)
    
    If Err Then
        If iFoutSelectieTeller < 1 Then MsgBox "Verkeerd geselecteerd", vbCritical, "Let op"
        Err.Clear
        'RetObj.Highlight (False)
        iFoutSelectieTeller = iFoutSelectieTeller + 1
        GoTo Opnieuw1
    End If
    
    
    If RetObj.EntityName = "AcDbPolyline" Or RetObj.EntityName = "AcDbLine" Then
    Else
        If iFoutSelectieTeller < 1 Then MsgBox "Geen line of polyline geselecteerd", vbCritical
        iFoutSelectieTeller = iFoutSelectieTeller + 1
        GoTo Opnieuw1
        'End
    End If
   
    '-----------------------------------------------------------------------
    ' GESELECTEERDE POLYLINE IN LAAG LEGPLAN ZETTEN
    '-----------------------------------------------------------------------
    
    If RetObj.EntityName = "AcDbPolyline" Then
        RetObj.Highlight (True)
        Call AanmakenLaag("Legplan", 2, False)
        RetObj.Layer = "Legplan"
    End If
    
    
    '-----------------------------------------------------------------------
    ' OSNAP WEER TERUGZETTEN
    '-----------------------------------------------------------------------
'
'    ThisDrawing.SetVariable "OSMODE", iOsmode
    
    '-----------------------------------------------------------------------
    ' LAAG "LEGPLANOMTREK" AANZETTEN.
    '-----------------------------------------------------------------------
        
    ThisDrawing.Layers.Item("Legplanomtrek").LayerOn = True
    If Err Then
        Err.Clear
    End If

    '-----------------------------------------------------------------------
    ' GEEF OFFSET RICHTING (EN DAARMEE AANTAL AAN)
    '-----------------------------------------------------------------------

opnieuw:

    Dim sAantal As String
    Dim Aantal As Integer
    Dim p2 As Variant
    Dim sMelding As String
    Dim sAntw As String
    
    'AANTAL OPGEVEN EN RICHTING AANWIJZEN
    If F_Main.CheckBox10.Value = True Then
        sMelding = "Geef offset-richting aan:"
        
        sAantal = InputBox("Geeft aantal groepen op.", "Aantal groepen", "2")
        If sAantal = "" Then Exit Sub
        
        If sAantal = Val(sAantal) Then
            Aantal = Val(sAantal)
            Aantal = Aantal * 2
            
            ' CONTROLE INDIEN > 9 GROEPEN
            If Aantal > 18 Then
                sAntw = MsgBox("Meer dan 10 groepen plaatsen ?", vbYesNo, "Offset leidingen")
                If sAntw = vbNo Then GoTo opnieuw
            End If
            
            
            
        Else
            MsgBox " verkeerde waarde Invoer Aantal:" & sAantal, vbInformation
        End If
    Else
        ' EINDPUNT EN RICHTING AANWIJZEN:
        sMelding = "Geef aan tot waar de offset-polylines (leidingen) moeten komen:"
    End If
    
    p2 = ThisDrawing.Utility.GetPoint(p1, sMelding)
    If Err Then
        Err.Clear
        End
    End If
    
        
        
        

   
    
   
    '-----------------------------------------------------------------------
    ' BEPAAL DE AANTAL OFFSETS
    '-----------------------------------------------------------------------
    
    Dim dLengte As Double
    
    If F_Main.CheckBox10.Value = False Then
        dLengte = Lengte(p1, p2)
        Aantal = dLengte / dHOH
    End If
    
    ''Aantal = Aantal / 2
    'MsgBox "Aantal offset is: " & Aantal
    
    
    '6 aug 2003
    'indien gekozen voor duo, dan c.a. 2x zo veel als geselecteerde punt (behalve als aantal opgeven wordt.)
    If F_Main.CheckBox9.Value = True And F_Main.CheckBox10.Value = False Then
        Aantal = Aantal * 4
        If Aantal Mod (2) <> 0 Then Aantal = Aantal + 1
    End If
    
    
    
    '-----------------------------------------------------------------------
    ' MAAK EERST EEN TEST OFFSET (0.5 hoh), OM TE KIJKEN OF RICHTING GOED IS
    '-----------------------------------------------------------------------
    
'    LET OP: + WAARDE BIJ OFFSET, BETEKENT DAT DE KOPIE GROTER WORDT
'    The distance to offset the object.
'    The offset can be a positive or negative number, but it cannot equal zero.
'    If the offset is negative, this is interpreted as being an offset to make a "smaller"
'    curve (that is, for an arc it would offset to a radius that is
'    "Distance less" than the starting curve's radius).
'    If "smaller" has no meaning, then it would offset
'    in the direction of smaller X, Y, and Z WCS coordinates.

    
    OffsetObj = RetObj.Offset(dHOH / 2)
    'OffsetObj(0).Color = acMagenta
    
    'LET OP: UPDATE MOET ANDERS ZAL SELECTIESET FENCE DEZE NIET VINDEN !!
    OffsetObj(0).Update
        
    'MsgBox OffsetObj(0).handle
    
    '--------------------------------------------------------------------------
    ' SELECTIESET FENCE AANMAKEN (OP HULP-OFFSET-POLYLINE) OM TE CONTROLEREN
    ' OF DE OFFSET-RICHTING GOED WAS.
    '--------------------------------------------------------------------------
    
    Call SelectiesetsVerwijderen
    
    Dim ssetObj As AcadSelectionSet
    Set ssetObj = ThisDrawing.SelectionSets.Add("SSET")
        
    
    Dim mode As Integer
    Dim pointsArray(0 To 5) As Double
    mode = acSelectionSetFence
    
    pointsArray(0) = p1(0):     pointsArray(1) = p1(1):     pointsArray(2) = 0
    pointsArray(3) = p2(0):     pointsArray(4) = p2(1):     pointsArray(5) = 0
    
        
    ssetObj.SelectByPolygon mode, pointsArray
    'LET OP DUS GEEN ssetObj.Select mode, pointsArray

    
    Dim element As Object
    Dim bJuisteOffsetRichting As Boolean
    
    For Each element In ssetObj
        'MsgBox OffsetObj(0).handle
        If element.handle = OffsetObj(0).handle Then bJuisteOffsetRichting = True
    Next element
    
    
    ssetObj.Clear
    ssetObj.Delete
    
    'MsgBox "bJuisteOffsetRichting = " & bJuisteOffsetRichting
        
      
    '-----------------------------------------------------------------------
    ' VOORGAANDE HULP-OFFSET VERWIJDEREN
    '-----------------------------------------------------------------------

    OffsetObj(0).Erase
    
    '-----------------------------------------------------------------------
    ' ALLE OFFSET-POLYLINES PLAATSEN IN DE JUISTE RICHTING
    '-----------------------------------------------------------------------

    If F_Main.CheckBox5.Value = True And RetObj.EntityName <> "AcDbPolyline" Then MsgBox "De beginpunten van de lijnen worden alleen gelijk gemaakt voor (aanvoer/ retour) polylines.", vbInformation, "WTH-Offset"
        
    Dim t As Integer
    'Dim S As Integer    'sign, plus of min
    Dim LaatsteOffsetObj As AcadEntity
    
    
'''     ORIGINEEL VOOR 7 APRIL 2003
'''     For t = 1 To Aantal
'''        If bJuisteOffsetRichting = True Then
'''            OffsetObj = RetObj.Offset(t * dHOH)
'''        Else
'''            OffsetObj = RetObj.Offset(-t * dHOH)
'''        End If
    
'''     NIEUW OP 7 APRIL 2003


    
     Dim c As Double
     For t = 1 To Aantal
        
        ''' NIEUW INBOUW VAN DUOLEIDING-MOGELIJKHEID 6 AUG 2003
        'offset instellen d.m.v. counter (c)
        If F_Main.CheckBox9.Value = False Then
            'geen duo-leidingen
            c = c + 1
        Else
            'wel duo-leidingen
            If t > 1 Then
                    'duo-leidingen, offset is altijd 1 cm en tussenliggend 0.5 HOH
                    If t Mod (2) = 0 Then
                        'c = c + (1 / dHOH)                      'offset van 1 cm
                        c = c + (2 / dHOH)                      'offset van 2 cm   (gewijzigd 10 feb 2004)
                    Else
                        '*** origineel 14 feb 2004: 'c = c + ((1 / dHOH) * (dHOH / 2))       'offset van 1cm x 0.5 HOH
                         c = c + ((1 / dHOH) * dHOH)        'offset van 1cm x 0.5 HOH
                    End If
            Else
                    '*** origineel 14 feb 2004:
                    'c = c + 0.5    'dan is eerste offsetlijn 0.5 HOH
                    c = c + 1       'dan is eerste offsetlijn 1 HOH
            End If
        End If
     

        If bJuisteOffsetRichting = True Then
                If F_Main.CheckBox7 Then
                    'start met halve hoh-afstand
                    '***origineel 14 feb 2004:
                    OffsetObj = RetObj.Offset((c * dHOH) - (0.5 * dHOH))
                     'OffsetObj = RetObj.Offset((c * dHOH) - (dHOH))
                Else
                    'start met hele hoh-afstand
                    OffsetObj = RetObj.Offset(c * dHOH)
                    
                End If
                
        Else
                If F_Main.CheckBox7 Then
                    'start met halve hoh-afstand
                    '*** origineel 14 feb 2004
                    OffsetObj = RetObj.Offset((-c * dHOH) + (0.5 * dHOH))
                    'OffsetObj = RetObj.Offset((-c * dHOH) + dHOH)
                Else
                    'start met hele hoh-afstand
                    OffsetObj = RetObj.Offset(-c * dHOH)
                End If
        End If


        'MsgBox "wachten"
                        
        'OffsetObj.Layer = RetObj.Layer
        
        
        'BEGINPUNTEN VAN LWT-POLYLINE GELIJK MAKEN AAN BEGINPUNT VAN GESELECTEERDE POLYLINE.
        If F_Main.CheckBox5.Value = True Then
            Set LaatsteOffsetObj = ThisDrawing.ModelSpace.Item(ThisDrawing.ModelSpace.Count - 1)
            
            
            'Dim intVCnt As Integer
            'Dim varVert As Variant
            Dim coord As Variant
            
            coord = RetObj.Coordinate(0)
            coord(0) = coord(0)
            LaatsteOffsetObj.Coordinate(0) = coord
            LaatsteOffsetObj.Update
        End If
        
        
    Next t
    
    'INDIEN GEKOZEN IS OM DE EERSTE POLYLINE MET HALVE HOH TE OFFSETTEN (Start halve hoh)
    'DAN AUTOMATISCH EERSTE GESELECTEERDE POLYLINE VERWIJDEREN (ERASE)
    '+ automatisch vragen of legpatroon opgeschoven moet worden.
    
    Dim antw As String
    If F_Main.CheckBox7 Then
        RetObj.Delete
        
        antw = MsgBox("Legpatroon opschuiven ?", vbQuestion + vbYesNo, "Doorgaan met opschuiven")
        If antw = vbYes Then Call F_Main.OpschuivenLegpatroon
    End If
    
    '* nieuw 21 mei 2003
    'MsgBox "tot hier 5 mei 2004: end verwijderd", vbExclamation
    
    'End
End Sub



   'DUO
'''                    If t Mod 2 = 0 Then
'''                        OffsetObj = RetObj.Offset(t * dHOH / 2)
'''                    Else
'''                        OffsetObj = RetObj.Offset(t * dHOH / 2 - 2)
'''                    End If
'''

Attribute VB_Name = "M_3PlaatsenArcsNew"
Public Veld(0 To 500) As String

Public Sub PlaatsenArcsNew()

    F_Main.Hide
    On Error Resume Next
    
    Dim KleurNr As Integer
    Dim KleurOrgNr As Integer
    
    KleurNr = 1
    
    '------------------------------------------------------------------
    ' EERST REGENEREREN ANDERS SOMS NIET GOED
    '------------------------------------------------------------------
    '*verplaatst 21 mei 2003
    'ThisDrawing.Regen acActiveViewport
    

    '------------------------------------------------------------------
    ' AANGEVEN BEGIN EN EINDPUNT VAN FENCE SELECTIE-LIJN
    '------------------------------------------------------------------
    
 
    Dim ReturnObj1 As AcadObject
    Dim returnObj2 As AcadObject
    Dim bStartpointGevonden As Boolean

    Dim p1 As Variant
    Dim p2 As Variant
    
    
       
    Dim iFoutSelectieTeller As Integer
    
Opnieuw1:

    '*** voor 27 jan 2004 was dit: If iFoutSelectieTeller > 1 Then End
    If iFoutSelectieTeller > 1 Then End
 
    ThisDrawing.Utility.GetEntity ReturnObj1, p1, "Selecteer beginpunt van de eerste leiding"
    
    
    
    If Err Then
        Err.Clear
        If iFoutSelectieTeller < 1 Then MsgBox "Verkeerde selectie", vbCritical, "Let op"
        iFoutSelectieTeller = iFoutSelectieTeller + 1
        GoTo Opnieuw1
        
    End If
    If ReturnObj1.EntityName <> "AcDbLine" Then
        MsgBox "Geen lijn geselecteerd.", vbCritical, "Let op"  ': End
        iFoutSelectieTeller = iFoutSelectieTeller + 1
        GoTo Opnieuw1
    End If
        
    KleurOrgNr = ReturnObj1.Color
    ReturnObj1.Color = KleurNr
    
    
    iFoutSelectieTeller = 0
    
Opnieuw2:

    If iFoutSelectieTeller > 1 Then End
    
    ThisDrawing.Utility.GetEntity returnObj2, p2, "Selecteer de tweede leiding."
    
    
    
    If Err Then
        Err.Clear
        If iFoutSelectieTeller < 1 Then MsgBox "Verkeerde selectie", vbCritical, "Let op"
        ReturnObj1.Color = KleurOrgNr
        
        iFoutSelectieTeller = iFoutSelectieTeller + 1
        GoTo Opnieuw2
        
    End If
    If returnObj2.EntityName <> "AcDbLine" Then
        MsgBox "Geen lijn geselecteerd.", vbCritical, "Let op"
        ReturnObj1.Color = KleurOrgNr
        
        iFoutSelectieTeller = iFoutSelectieTeller + 1
        GoTo Opnieuw2
    End If
    'returnObj2.Color = KleurNr
    
    If ReturnObj1.handle = returnObj2.handle Then
        MsgBox "Tweemaal dezelfde lijn geselecteerd.", vbExclamation, "Let op"
        End 'Exit Sub
    End If
    
    'ZOOMEN ANDERS VERKEERDE SELECTIESET:
    ZoomExtents
    '* NIEUW OP 21 MEI 2003 !!!
    ThisDrawing.Regen acActiveViewport
    
    'BEPALEN OF BEGIN OF EINDPUNT VAN DE LIJN GESELECTEERD IS.
    
    If Lengte(ReturnObj1.EndPoint, p1) > Lengte(ReturnObj1.StartPoint, p1) Then bStartpointGevonden = True
    'MsgBox "bStartpointGevonden=" & bStartpointGevonden

    '* 20 mei 2003 er bij geschreven
    If bStartpointGevonden = True Then bBijStartpointBeginnen = True

'''''    '* 20 mei 2003 uitgezet want is niet van toepassing (berekening stond er eigenlijk al boven)
'''''    '------------------------------------------------------------------
'''''    ' BEPALEN AAN WELKE ZIJDE BEGINNEN (BEGINLEIDING, PUNT P1)
'''''    '------------------------------------------------------------------
''''''    Dim bBijStartpointBeginnen As Boolean
''''''    If Lengte(P1, ReturnObj1.EndPoint) > Lengte(P1, ReturnObj1.StartPoint) Then
''''''        'MsgBox "Bij startpoint van de eerste lijn beginnen"
''''''        bBijStartpointBeginnen = True
''''''    Else
''''''        'MsgBox "Bij endpoint van de eerste lijn beginnen"
''''''        bBijStartpointBeginnen = False
''''''    End If
    

    '------------------------------------------------------------------
    ' AANMAKEN SELECTIESET MBV FENCE
    '------------------------------------------------------------------
 
    Dim ssetObj As AcadSelectionSet
    Dim mode As Integer
    Dim pointsArray(0 To 5) As Double
    
    'MsgBox "hier fout"
    
    For Each ssetObj In ThisDrawing.SelectionSets
        ssetObj.Clear
        ssetObj.Delete
    Next ssetObj
    
    
    Set ssetObj = ThisDrawing.SelectionSets.Add("SSET")
    mode = acSelectionSetFence
    
    pointsArray(0) = p1(0):     pointsArray(1) = p1(1):     pointsArray(2) = 0
    pointsArray(3) = p2(0):     pointsArray(4) = p2(1):     pointsArray(5) = 0
    
    
    ssetObj.SelectByPolygon mode, pointsArray
    'MsgBox "ssetObj.count=" & ssetObj.Count
  
    
    '---------------------------------------------------------------------------------------------------------
    ' * nieuw 21 mei 2003 (BIJ ONEVEN AANTAL GING AFRONDEN NIET ALTIJD GOED)
    '
    ' CONTROLEREN OF DE TWEE GESLECTEERDE LIJNEN OOK IN DE SELECTIE ZITTEN
    ' DEZE ANDERS TOEVOEGEN IN SELECTIESET
    ' INDIEN ONEVEN-AANTAL ELEMENTEN IN SELECTIESET, DAN LAATST GESELECTEERDE LIJN VERWIJDEREN
    '---------------------------------------------------------------------------------------------------------
            
    
    Dim element As Object
    Dim bReturnObj1Gevonden As Boolean
    Dim bReturnObj2Gevonden As Boolean
    
    'CONTROLEREN OF GESELECTEERDE LIJN IN SELECTIESET AANWEZIG IS, ANDERS TOEVOEGEN
    For Each element In ssetObj
        'element.Color = acGreen
        If element.handle = ReturnObj1.handle Then bReturnObj1Gevonden = True
        If element.handle = returnObj2.handle Then bReturnObj2Gevonden = True
    Next element
    
    Dim addObjects(0) As AcadEntity
    Set addObjects(0) = ReturnObj1
    If bReturnObj1Gevonden = False Then ssetObj.AddItems addObjects
    
    Set addObjects(0) = returnObj2
    If bReturnObj2Gevonden = False Then ssetObj.AddItems addObjects
    
    'MsgBox ssetObj.Count
    
    'INDIEN ELEMENTEN NIET IN LAAG LEGPLAN OF GROEP_ DAN VERWIJDEREN UIT SELECTIESET
    Dim removeObjects(0) As AcadEntity
    
    If F_Main.CheckBox8.Value = True Then
        For Each element In ssetObj
            'element.Color = acGreen
            If element.Layer = "Legplan" Or Left$(element.Layer, 6) = "groep_" Then
            Else
                Set removeObjects(0) = element
                ssetObj.RemoveItems removeObjects
            End If
        Next element
    End If
    'MsgBox ssetObj.Count
           
      
                        
    
    'INDIEN EEN ONEVEN AANTAL LIJNEN IN SELECTIESET,DAN LAATST GESELECTEERDE LIJN VERWIJDEREN
    'Dim removeObjects(0) As AcadEntity
    If ssetObj.Count Mod 2 <> 0 Then
        Set removeObjects(0) = returnObj2
        ssetObj.RemoveItems removeObjects
    End If
    
    'MsgBox ssetObj.Count

'    For Each element In ssetObj
'        element.Color = acMagenta
'    Next element
    
    
    '---------------------------------------------------------------------------------------------------------
    ' UITLEZEN WELKE LEIDINGEN IN SELECTIESET ZITTEN, Y-BEGINPUNT LIJN + GEVONDEN HANDLES IN ARRAY ZETTEN
    ' ofwel in array: beginY/handle (zodat dit gesorteerd kan worden)
    '---------------------------------------------------------------------------------------------------------
        
   
    
    'Dim element As Object          'HIERBOVEN GEDECLAREERD
    Dim ArrHandles() As String

    ReDim Preserve ArrHandles(0)
    Dim bWelAfronden As Boolean
    Dim iLijnteller As Integer

    
    
     For Each element In ssetObj

            bWelAfronden = False
            If element.EntityName = "AcDbLine" Then


                    If F_Main.CheckBox8.Value = True Then
                        If element.Layer = "Legplan" Or Left$(element.Layer, 6) = "groep_" Then bWelAfronden = True
                    Else
                        bWelAfronden = True
                    End If

                    If bWelAfronden = True Then
                        iLijnteller = iLijnteller + 1

                        element.Color = KleurNr
                        element.Update

                        'MsgBox Element.handle
                        '((Element.Highlight True)) ZIE ARRAY
                        'VULLEN ARRAY
                        ReDim Preserve ArrHandles(UBound(ArrHandles) + 1)
                        ArrHandles(UBound(ArrHandles)) = element.handle
                    End If


            End If
    Next element

   
    ssetObj.Clear
    ssetObj.Delete
    
    '--------------------------------------------------------------------------------------
    ' CONTROLEREN HOEVEEL LIJNEN ER GEVONDEN ZIJN.
    '--------------------------------------------------------------------------------------
   
    If iLijnteller = 0 Then
        MsgBox "Geen lijnen gefilterd. (verkeerde lagen > vink optie uit)", vbExclamation, "Geen lijnen gevonden."
        Exit Sub
    End If
    
    
    
'''''   ONDERSTAANDE ROUTINE NIET MEER NODIG DOOR AANPASSINGEN 21 MEI 2003
'''''    '--------------------------------------------------------------------------------------
'''''    ' UITLEZEN ARRAY MET DE HANDLES EN CONTROLEREN OF HANDLE VAN DE TWEE GESELECTEERDE
'''''    ' LIJNEN IN ARRAY BESTAAT, ANDERS TOEVOEGEN.
'''''    '--------------------------------------------------------------------------------------
'''''
'''''
'''''    Dim t As Integer
'''''    Dim bHandleEersteLijnGevonden As Boolean
'''''    Dim bHandleTweedeLijnGevonden As Boolean
'''''
'''''
'''''    For t = LBound(ArrHandles) + 1 To UBound(ArrHandles)            ' + 1 anders wordt eerste lege veld afgebeeld
'''''        'MsgBox ArrHandles(t), vbExclamation
'''''
'''''        If ArrHandles(t) = ReturnObj1.handle Then bHandleEersteLijnGevonden = True
'''''        If ArrHandles(t) = returnObj2.handle Then bHandleTweedeLijnGevonden = True
'''''    Next t
'''''
'''''    If bHandleEersteLijnGevonden = False Then
'''''        'TOEVOEGEN HANDLE VAN EERSTE GESELECTEERDE LIJN
'''''        ReDim Preserve ArrHandles(UBound(ArrHandles) + 1)
'''''        ArrHandles(UBound(ArrHandles)) = ReturnObj1.handle
'''''    End If
'''''
'''''    If bHandleTweedeLijnGevonden = False Then
'''''         'TOEVOEGEN HANDLE VAN TWEEDE GESELECTEERDE LIJN
'''''        ReDim Preserve ArrHandles(UBound(ArrHandles) + 1)
'''''        ArrHandles(UBound(ArrHandles)) = returnObj2.handle
'''''    End If
    
'''''    '--------------------------------------------------------------------------------------
'''''    ' TELLEN VAN HET AANTAL GESLECTEERDE LEIDINGEN
'''''    '--------------------------------------------------------------------------------------
'''''
'''''    'MsgBox "Er zijn " & UBound(ArrHandles) & " leidingen geselecteerd", vbInformation, "Leiding selectie"
'''''
'''''    Dim bEvenAantal As Integer
'''''    If UBound(ArrHandles) Mod 2 = 0 Then
'''''        bEvenAantal = True
'''''        MsgBox "Even aantal", vbExclamation
'''''    Else
'''''         bEvenAantal = False
'''''
'''''        '* 21 mei gewijzigd in true
'''''        'bEvenAantal = True
'''''
'''''        '19 mei 2003 melding uitgezet
'''''        MsgBox "Oneven aantal leidingen !", vbExclamation, "Let op"
'''''    End If
    
    
    bEvenAantal = True
    
    '--------------------------------------------------------------------------------------
    ' TEST UITLEZEN HANDLES
    '--------------------------------------------------------------------------------------
'    For t = LBound(ArrHandles) + 1 To UBound(ArrHandles)            ' + 1 anders wordt eerste lege veld afgebeeld
'        MsgBox LeesHandle(ArrHandles(t))
'    Next t

    '--------------------------------------------------------------------------------------
    ' ROTEREN GESELCTEERDE LIJNEN
    '(UITLEZEN ARRAY MET DE HANDLES EN OP 0 GRADEN ROTEREN + HIGHLIGHTEN)
    '--------------------------------------------------------------------------------------
    
    Dim LijnObj As AcadLine
    Dim RotHoek As Double
    
    RotHoek = ReturnObj1.Angle
    Dim Pbegin As Variant
    Dim Peind As Variant
    Dim Ptemp As Variant
    
    Dim Y() As String
    ReDim Preserve Y(0)
    
    'Dim sHandle As String
    
    For t = LBound(ArrHandles) + 1 To UBound(ArrHandles)            ' + 1 anders wordt eerste lege veld afgebeeld
        
        Set LijnObj = ThisDrawing.HandleToObject(ArrHandles(t))
        LijnObj.Color = KleurOrgNr
        
        'RECHT ROTEREN LIJNEN (OP NUL GRADEN):
        LijnObj.Rotate ReturnObj1.EndPoint, -RotHoek
        'LijnObj.Highlight True
        
        
        'BEPALEN OF LIJNEN RECHT LIGGEN:
        Pbegin = LijnObj.StartPoint
        Peind = LijnObj.EndPoint
        'MsgBox Pbegin(1) & Chr(10) & Chr(13) & Peind(1), vbExclamation
        If Round(Pbegin(1), 1) <> Round(Peind(1), 1) Then MsgBox "De leiding met handle " & LijnObj.handle & " heeft een andere hoek dan de geselecteerde leiding.", vbCritical, "Let op": End
            
            
        'Y-COORDINAAT INVULLEN IN ARRAY (Y-BEGINPUNT = Y-EINDPUNT, WANT LIJNEN OP 0 GRADEN !)
        ReDim Preserve Y(UBound(Y) + 1)
        Y(UBound(Y)) = Pbegin(1)
         
         
        'ZELFDE RICHTING ROTEREN LIJNEN, BEGINPUNT LINKS VAN EINDPUNT ANDERS DRAAIEN
        Pbegin = LijnObj.StartPoint
        Peind = LijnObj.EndPoint
        If Pbegin(0) > Peind(0) Then
        'beginpunt van lijn ligt rechts van eindpunt, daarom omdraaien.
            Ptemp = LijnObj.EndPoint
            LijnObj.EndPoint = LijnObj.StartPoint
            LijnObj.StartPoint = Ptemp
        End If
        
        'handle in array overschrijven met y-coordinaat & "/" &  handle
        ArrHandles(t) = ycoordENhandle(LijnObj)
        
        
        '*** VULLEN ARRAY VELD (DEZE LATER SORTEREN !)
        Veld(t) = ycoordENhandle(LijnObj)
        
        
    Next t
    
    'sHandle = LeesHandle(ArrHandles(t))
   
    
    '**************************************************************************************
    ' (1) OP VOLGORDE SORTEREN VAN DE LIJNEN (OP Y-COORDINAAT) + ARCS PLAATSEN
    '**************************************************************************************

    'MsgBox "einde array", vbInformation
    
    
    'SORTEREN GEGEVENS:
    Call BubbleSort
    
'''    Debug.Print "*******************"
'''    Debug.Print Time
'''    Debug.Print "*******************"
'''    For x = 0 To UBound(Veld) '- 1
'''        Debug.Print Veld(x)
'''    Next x
'''
'''    MsgBox "tot hier 30 mei 2003"
'''    End
    
'''    'GESORTEERDE GEGEVENS UITLEZEN UIT ARRAY:
'''    Dim x As Integer
'''    For x = 0 To UBound(Veld)
'''        'MsgBox Veld(x)
'''        If Veld(x) <> "" Then
'''            MsgBox Veld(x), vbInformation, "GESORTEERD"
'''            Debug.Print Veld(x)
'''        End If
'''    Next x
            
    
    '--------------------------------------------------------------------------------------
    ' EXTRA ZOOMEXTENTS 30 MAART 2003 (WANT SOMS FOUTEN BIJ HET TERUGPLAATSEN/ ROTEREN)
    '--------------------------------------------------------------------------------------
   
   ZoomExtents
   
   
    '**************************************************************************************
    ' (2) OP VOLGORDE SORTEREN VAN DE LIJNEN (OP Y-COORDINAAT) + ARCS PLAATSEN
    '**************************************************************************************
    
    
    'GESORTEERDE ARRAY !
    Dim LijnObj2 As AcadLine
    
    Dim Plijn1Beginpunt As Variant
    Dim Plijn2Beginpunt As Variant
    Dim Plijn1Eindpunt As Variant
    Dim Plijn2Eindpunt As Variant
    Dim Pnew(0 To 2) As Double       'nieuwe start of eindpunt van de lijn (inkorten na plaatsen arc)
    
    
    Dim Centerp(0 To 2) As Double
    Dim PuntObj As AcadPoint
    Dim Radius As Double
    Dim ArcObj As AcadArc
    
    Dim sHandle1 As String
    Dim sHandle2 As String
    Dim pos As Integer
    
    Dim ModIsWaar As Boolean
    
    
    'UITLEZEN GESORTEERD ARRAY:
    For x = 0 To UBound(Veld) '- 1
        'MsgBox Veld(x)
        If Veld(x) <> "" Then
            'Debug.Print Veld(X)
            
            pos = InStr(1, Veld(x), "/", vbTextCompare)
            sHandle1 = Right(Veld(x), Len(Veld(x)) - pos)
            
            pos = InStr(1, Veld(x + 1), "/", vbTextCompare)
            sHandle2 = Right(Veld(x + 1), Len(Veld(x + 1)) - pos)
            
            'afbeelden y-coordinaat van geroteerde lijnen + handle
            'Debug.Print sHandle
            'MsgBox "sHandle=" & sHandle
            
        'End If
        'Next x
    
    



        'EERSTE LIJN UIT LIJST (ARRAY)
         Set LijnObj = ThisDrawing.HandleToObject(sHandle1)
         Plijn1Beginpunt = LijnObj.StartPoint
         Plijn1Eindpunt = LijnObj.EndPoint


        'BIJ LAATSTE LIJN, DEZE TERUGDRAAIEN EN EINDE
        'OF DIT WEG EN FOR T =.... -1 !!!! ZIE HIERBOVEN.
'        If t = UBound(ArrHandles) Then
'            LijnObj.Rotate returnObj1.EndPoint, RotHoek
'            LijnObj.Highlight True
'            'MsgBox "Laatste lijn: " & ArrHandles(t)
'            End
'        End If


          'TWEEDE LIJN UIT LIJST (ARRAY)
         'If t < UBound(ArrHandles) - 1 Then
            Set LijnObj2 = ThisDrawing.HandleToObject(sHandle2)
            
            
            '*** nieuw 30 mei 2003:
            If Err Then
                '* 30 mei 2003, bij overgang van negatieve naar positieve y-coordinaat
                'van de gefilterde lijnen ontstaat error want in array zitten 500
                'elementen waaronder veel lege velden: deze worden
                'door de filter (bubblesort) routine tussen de positieve en nagatieve y-waarden ingeplaatst !
                Err.Clear
            End If
            
            Plijn2Beginpunt = LijnObj2.StartPoint
            Plijn2Eindpunt = LijnObj2.EndPoint
         'End If


        '----------------------------------------------------------------------------------
        'PLAATSEN ARC
        '----------------------------------------------------------------------------------
        
        'AANGEVEN RICHTING (BEGINPUNT OF EINDPUNT VAN EERSTE LEIDING)
        If x Mod 2 <> 0 Then
            If bBijStartpointBeginnen = True Then
                ModIsWaar = False
            Else
                ModIsWaar = True
            End If
        Else
            If bBijStartpointBeginnen = True Then
                ModIsWaar = True
            Else
                ModIsWaar = False
            End If
        End If
        
        'INDIEN ONEVEN AANTAL LEIDINGEN, DAN 'RICHTING' OMKEREN:
        If bEvenAantal = False Then ModIsWaar = Not (ModIsWaar)
        
        
        If ModIsWaar = True Then
            'ARCS AAN DE BEGINZIJDE (LINKS):

            'X-PUNT ARCCENTER (IS GELIJK AAN BEGINPUNT VAN KORTSTE LIJN):
            If Plijn1Beginpunt(0) > Plijn2Beginpunt(0) Then
                Centerp(0) = Plijn1Beginpunt(0)

                Pnew(0) = Plijn1Beginpunt(0)            '2 ipv 1 !!!
                Pnew(1) = Plijn2Beginpunt(1)
                LijnObj2.StartPoint = Pnew
                LijnObj2.Color = KleurOrgNr
                'LijnObj2.Color = acMagenta
            Else
                Centerp(0) = Plijn2Beginpunt(0)

                Pnew(0) = Plijn2Beginpunt(0)
                Pnew(1) = Plijn1Beginpunt(1)
                LijnObj.StartPoint = Pnew
                'LijnObj.Color = acGreen
                LijnObj.Color = KleurOrgNr
            End If

            'Y-PUNT ARCCENTER:
            Centerp(1) = (Plijn1Beginpunt(1) + Plijn2Beginpunt(1)) / 2
            Radius = Abs(Plijn1Beginpunt(1) - Plijn2Beginpunt(1))       'dit is de hoh
            Radius = Radius / 2
            If Radius <> 0 Then Set ArcObj = ThisDrawing.ModelSpace.AddArc(Centerp, Radius, 1.5707963267949, 4.71238898038469)

        Else
            'ARCS AAN DE EINDZIJDE (RECHTS):

            'X-PUNT ARCCENTER (IS GELIJK AAN EINDPUNT VAN KORTSTE LIJN):
            If Plijn1Eindpunt(0) < Plijn2Eindpunt(0) Then
                Centerp(0) = Plijn1Eindpunt(0)

                Pnew(0) = Plijn1Eindpunt(0)
                Pnew(1) = Plijn2Eindpunt(1)
                LijnObj2.EndPoint = Pnew
                'LijnObj2.Color = acMagenta
                LijnObj2.Color = KleurOrgNr
            Else
                Centerp(0) = Plijn2Eindpunt(0)

                Pnew(0) = Plijn2Eindpunt(0)
                Pnew(1) = Plijn1Eindpunt(1)
                LijnObj.EndPoint = Pnew
                LijnObj.Color = KleurOrgNr
            End If

            'Y-PUNT ARCCENTER:
            Centerp(1) = (Plijn1Eindpunt(1) + Plijn2Eindpunt(1)) / 2
            Radius = Abs(Plijn1Eindpunt(1) - Plijn2Eindpunt(1))       'dit is de hoh
            Radius = Radius / 2
            If Radius <> 0 Then Set ArcObj = ThisDrawing.ModelSpace.AddArc(Centerp, Radius, 4.71238898038469, 1.5707963267949)

         End If


        'TERUG DRAAIEN ARC EN LINES
        If Radius <> 0 Then
            ArcObj.Rotate ReturnObj1.EndPoint, RotHoek
            ArcObj.Highlight True
        End If

        ArcObj.Color = KleurOrgNr
        
        'nieuw 1 april 2003:
        'arcobj.Layer = ReturnObj1.Layer
        
        ArcObj.Highlight True

        LijnObj.Rotate ReturnObj1.EndPoint, RotHoek
        LijnObj.Highlight True
        
        'test 30 maart 2003:
        'Punt (ReturnObj1)
        'LijnObj.Update
        'MsgBox "wacht"


        End If
    Next x


 'WEER TERUGZOOMEN:
 ZoomPrevious
 '* 21 mei 2003 extra zoomprevious want ging niet terug naar begin
 ZoomPrevious
    
End Sub

Function ycoordENhandle(Object As AcadObject) As String

    'object = line

    Dim Beginpunt As Variant
    Dim Xbegincoord As Double

    Beginpunt = Object.StartPoint
    Xbegincoord = Beginpunt(1)
    Xbegincoord = Round(Xbegincoord, 0)
    

    ycoordENhandle = Xbegincoord & "/" & Object.handle
End Function

Function LeesHandle(zoekstring As String) As String
    Dim pos As Integer
    pos = InStr(1, zoekstring, "/")
    LeesHandle = Right(zoekstring, Len(zoekstring) - pos)
End Function

  
''''------------------------------------------------------------------------------------------------
''''PRINCIPE ARRAY: (SCHRIJVEN EN LEZEN)
''''------------------------------------------------------------------------------------------------

'''Public ArrLokatie() As String
'''
''''Dit boven de aanroep van het array plaatsen:
'''ReDim Preserve ArrLokatie(0)
'''
''''vullen array
'''ReDim Preserve ArrLokatie(UBound(ArrLokatie) + 1)
'''
'''ArrLokatie(UBound(ArrLokatie)) = sLokatie
'''
'''Uitlezen
'''Dim t As Integer
'''For t = LBound(ArrLokatie) + 1 To UBound(ArrLokatie)  ' + 1 anders wordt eerste lege veld afgebeeld
'''    MsgBox ArrLokatie(t)
'''Next t
''''------------------------------------------------------------------------------------------------




'------------------------------------------------------------------------------------------------
'SORTEREN VAN ARRAY-INHOUD MBV BUBBLESORT
'------------------------------------------------------------------------------------------------



'Sub TestSorteren()
'
'    Dim Veld(0 To 500)
'    Veld(0) = "AAA3"
'    Veld(1) = "AA1"
'    Veld(2) = "AA2"
'
'    Dim X%
'
'    Call BubbleSort(Veld)
'
'    For X = 0 To UBound(Veld)
'      If Veld(X) <> "" Then MsgBox Veld(X)
'    Next X
'End Sub
 
 
Private Sub BubbleSort()

''''    TEST: BEKIJKEN INHOUD VAN ARRAY "VELD"
''''    Dim XX As Integer
''''    For XX = 0 To UBound(Veld)
''''        If Veld(XX) <> "" Then MsgBox Veld(XX)
''''    Next XX
''''
    
    
  Dim LB As Integer     'of dim LB&
  Dim UB As Integer
  Dim TEMP$, pos&, x&
 
    LB = LBound(Veld)
    UB = UBound(Veld)
 
    While UB > LB
    
    
      pos = LB
 
      For x = LB To UB - 1
      
      '*** onderstaande regel is nieuw op 30 mei 2003 omdat filteren niet goed ging
      'bij de overgang van positieve en negatieve y-waarden. (want lege velden worden hier
      'blijkbaar tussen gesorteerd
      
      If Veld(x) <> "" And Veld(x + 1) <> "" Then
        
        '19 MEI 2003, DEZE REGEL UITGEZET. ARC'S PLAATSEN BIJ GROTE LEGPLANNEN GAAT NU WEL GOED !!
        'If Val(Veld(X)) < 0 Then MsgBox "Let op, leidingen met negatieve Y-waarde gevonden. Plaats de tekening in het eerste kwadrant (x>0 en Y>0 !).", vbCritical, "Afrondingen kunnen niet worden gemaakt": End
        
                
        
        'If Veld(x) > Veld(x + 1) Then                  'sorteren volgens ascii
        If Val(Veld(x)) > Val(Veld(x + 1)) Then         'sorteren volgens nummer
        
          TEMP = Veld(x + 1)
          Veld(x + 1) = Veld(x)
          Veld(x) = TEMP
          pos = x
        End If
        
        End If
      Next x
      
      'MsgBox Veld(x) & "    " & UBound(Veld)
 
      UB = pos
    
    Wend
    
'''    GESORTEERD ARRAY:
'''    For x = 0 To UBound(Veld)
'''        If Veld(x) <> "" Then MsgBox Veld(x), vbInformation
'''    Next x
    
End Sub

Attribute VB_Name = "M_4BepalenLengteNEW"


'------------------------------------------------------------------------------------
' !!!!  NIEUW FEBRUARI 2003: BEPALEN LENGTE POLYLINE T.O.V. SNIJPUNT MET LEIDING !!!!
'------------------------------------------------------------------------------------


Dim ArrHandle() As String
Dim ArrLengte() As Double
Dim sLaatseHandle As String

' Public PsnijpuntPublic as Variant   ' *** aangepast 21 mei 2003, nu double
Public PsnijpuntPublic(0 To 2) As Double


Private Sub CommandButton1_Click()
    
'    ReDim ArrHandle(0)
'    ReDim ArrLengte(0)

    Dim plineObj As AcadLWPolyline
    Dim LijnObj As AcadLine
    
    Set plineObj = ThisDrawing.ModelSpace.Item(0)
    Set LijnObj = ThisDrawing.ModelSpace.Item(1)

    Call M_BepalenLengteNEW.TekenLijnenOverPolyline(plineObj)
    Call M_BepalenLengteNEWBepalenSnijpunt(plineObj, LijnObj)

End Sub

Sub TekenLijnenOverPolyline(plineObj As AcadLWPolyline)

    ReDim ArrHandle(0)
    ReDim ArrLengte(0)

    '-----------------------------------------------------------------------
    'EXPLODEREN POLYLINE
    '----------------------------------------------------------------------
    
    Dim PolyObj As AcadLWPolyline
    'Set PolyObj = ThisDrawing.ModelSpace.Item(0)
    Set PolyObj = plineObj
    
    Dim ExplodedObj As Variant
    Dim I As Integer
    
    ExplodedObj = PolyObj.Explode
    'PolyObj.Explode 'dit mag ook indien geen return-objecten nodig
    
    ' DOORLOOP DE GEEXPLODEERDE ELEMENTEN: (ELEMENT 0 IS HET EERST GETEKENDE ELEMENT)
    
    For I = 0 To UBound(ExplodedObj)
        If I = 0 Then
            'ExplodedObj(I).Color = acYellow
            ExplodedObj(I).Layer = ThisDrawing.ActiveLayer.Name
        Else
            'ExplodedObj(I).Color = acYellow
            ExplodedObj(I).Layer = ThisDrawing.ActiveLayer.Name
        End If
        
        ExplodedObj(I).Update
        'MsgBox "Exploded Object " & I & ": " & ExplodedObj(I).ObjectName
    
        '---------------------------------------------------------------------
        'OPSLAAN HANDLES VAN DE LOSSEN ELEMENT (OM LATER LENGTE TE BEREKENEN)
        '---------------------------------------------------------------------
        
        'OPSLAAN HANDLE:
        ReDim Preserve ArrHandle(UBound(ArrHandle) + 1)
        ArrHandle(UBound(ArrHandle)) = ExplodedObj(I).handle
        
        Dim VorigeLengte As Double
        VorigeLengte = ArrLengte(UBound(ArrLengte))
        
        'OPSLAAN LINE-LENGTE OF ARC-LENGTE
        ReDim Preserve ArrLengte(UBound(ArrLengte) + 1)
        If ExplodedObj(I).EntityName = "AcDbLine" Then
            ArrLengte(UBound(ArrLengte)) = VorigeLengte + ExplodedObj(I).Length
        Else
            ArrLengte(UBound(ArrLengte)) = VorigeLengte + ExplodedObj(I).ArcLength
        End If
        
     Next
    

End Sub


Function BepalenSnijpunt(PolyObj As Object, LijnObj As Object) As Double

    '-------------------------------------------------------------
    'BEPALEN SNIJPUNT VAN LEIDING (LIJN) MET AANVOER-POLYLINE
    '-------------------------------------------------------------
    
    
     Dim intPoints As Variant
     Dim x As Double
     Dim Y As Double
     
     intPoints = LijnObj.IntersectWith(PolyObj, acExtendThisEntity)
    
     Dim I As Integer, j As Integer, k As Integer
     Dim str As String
     If VarType(intPoints) <> vbEmpty Then
         For I = LBound(intPoints) To UBound(intPoints)
             x = intPoints(j)
             Y = intPoints(j + 1)
             
             I = I + 2
             j = j + 3
             k = k + 1
         Next
    End If
    
    'origineel voor 25 mrt 2003
    'If k = 0 Then MsgBox "Geen snijpunt (leiding met retour-polyline) gevonden", vbCritical: End
    'nieuw
   
    If k = 0 Then
        'MsgBox "Geen snijpunt (leiding met retour-polyline) gevonden", vbCritical
        
        '5 mei 2004 dit uitgezet want lengte nu in modemacro geplaatst !
        'ThisDrawing.SetVariable "modemacro", "* geen snijp. gevonden. *"
        Exit Function
    End If
    
    '*** 21 mei 2003 deze regel uitgevinkt
    'If k > 1 Then MsgBox "Leiding heeft meerdere snijpunten met de aanvoer-leiding", vbCritical ': End
    
    '*** 21 mei 2003 deze regel nieuw
    If k > 1 Then SchrijfLogFile ("Leiding heeft meerdere snijpunten met de aanvoer-leiding")
    'Punt (intPoints)
    
      
    '----------------------------------------------------------------------------------
    'MAAK SELECTIESET (WINDOW) OP HET SNIJPUNT
    'OP DIT SNIJPUNT LIGT DE POLYLINE EN HIEROVER EEN LOSSE LINE OF ARC
    'VAN DIT LOSSE ELEMENT WORDT DE HANDLE BEPAALD OM VERVOLGENS DE LENGTE TE BEREKENEN
    '----------------------------------------------------------------------------------
    Dim point1(0 To 2) As Double
    Dim Point2(0 To 2) As Double
    
    point1(0) = x - 0.5
    point1(1) = Y - 0.5
    Point2(0) = x + 0.5
    Point2(1) = Y + 0.5
    
    Dim ssetObj As AcadSelectionSet
    Set ssetObj = ThisDrawing.SelectionSets.Add("SSET1")
    ssetObj.Select acSelectionSetCrossing, point1, Point2
    
    'MsgBox "Aantal elementen in selectieset"& ssetObj.Count

    Dim element As Object
    Dim LijnTeller As Integer
    Dim LaatsteObj As AcadEntity
    
    For Each element In ssetObj
        If element.EntityName = "AcDbLine" Or element.EntityName = "AcDbArc" Then
            'de volgende if is nieuw op 25 maart 2003
            'MsgBox Element.Layer
            'MsgBox Element.handle
            If element.Layer = ThisDrawing.ActiveLayer.Name Then
            If element.handle <> LijnObj.handle Then
                    LijnTeller = LijnTeller + 1
                    'MsgBox Element.handle
                    'Element.Color = acMagenta
                    Set LaatsteObj = element
            End If
            End If
        End If
    Next element
    
    
    'MsgBox "Laatste lijn (in het snijpunt) is: " & LaatsteObj.handle
    
    
    
    ssetObj.Clear
    ssetObj.Delete
    
    If LijnTeller = 0 Then MsgBox "Geen hulpsnijlijn gevonden": End
    'If LijnTeller > 1 Then MsgBox "Meer dan 1 hulpsnijlijn gevonden"    ': End
    'If LijnTeller > 1 Then MsgBox "Meer dan 1 hulpsnijlijn gevonden"
    If LijnTeller > 1 Then SchrijfLogFile ("* Meer dan 1 hulpsnijlijn gevonden bij het snijpunt met de geexplodeerde aanvoer-polyline.")
    
    
    sLaatseHandle = LaatsteObj.handle
    '-------------------------------------------------------------
    'ENDPOINT VAN GEVONDEN LIJN INKORTEN TOT SNIJPUNT
    '-------------------------------------------------------------
    Dim Peind(0 To 2) As Double
    Peind(0) = x
    Peind(1) = Y
    
    '*** 26 maart 2003 UITGEZET
    'If LaatsteObj.EntityName = "AcDbLine" Then LaatsteObj.EndPoint = Peind
    
    
    '-------------------------------------------------------------
    'BEPALEN LENGTE VAN DE VOORGAANDE LIJNSTUKKEN
    '-------------------------------------------------------------
    '*** 26 maart 2003 ORIGINEEL:
'    Dim LaatsteObjectLengte As Double
'    If LaatsteObj.EntityName = "AcDbLine" Then
'        LaatsteObjectLengte = LaatsteObj.Length
'    Else
'        LaatsteObjectLengte = LaatsteObj.ArcLength
'    End If
    
    
    Dim LaatsteObjectLengte As Double
    If LaatsteObj.EntityName = "AcDbLine" Then
        LaatsteObjectLengte = Lengte(LaatsteObj.StartPoint, Peind)
        'LaatsteObjectLengte = LaatsteObj.Length
    Else
        LaatsteObjectLengte = LaatsteObj.ArcLength
    End If
        
    
    
    
    Dim t As Integer                                'tellen lijnen (aanvoer over de polyline)
    Dim LengteTotSnijp As Double
    
    For t = 1 To UBound(ArrHandle)
        
        'MsgBox "handle=" & ArrHandle(t) & Chr(10) & Chr(13) & "totale lengte =" & ArrLengte(t)
        
        If ArrHandle(t) = LaatsteObj.handle Then
            LengteTotSnijp = ArrLengte(t - 1) + LaatsteObjectLengte
        End If
        
    Next t
    
    'MsgBox "Lengte polyline tot snijpunt=" & LengteTotSnijp
    
    BepalenSnijpunt = LengteTotSnijp
    
    ' *** uitgezet: dit gaat niet meer goed 21 mei 2003
    ' PsnijpuntPublic = intPoints         'opslaan om lengte van eerste lijn te kunnen bepalen
    PsnijpuntPublic(0) = x
    PsnijpuntPublic(1) = Y
    PsnijpuntPublic(2) = 0

End Function

Sub VerwijderenLosseLines()
    
    
    '-----------------------------------------------------------------------------
    'LOSSE LINES EN ARC VAN DE GEEXPLODEERDE POLYLINE VERWIJDEREN VANAF
    'HET LAATSTE ELEMENT BIJ HET SNIJPUNT
    'HET ARRAY MET HANDLES WORDT ACHTERSTEVOREN DOORLOPEN
    '------------------------------------------------------------------------------

    'MsgBox sLaatseHandle

    Dim t As Integer
    Dim LengteTotSnijp As Double
    Dim element As AcadEntity
    
    'For t = 1 To UBound(ArrHandle)
    For t = UBound(ArrHandle) To 1 Step -1
        
        'MsgBox ArrHandle(t)
        Set element = ThisDrawing.HandleToObject(ArrHandle(t))
        
        'EERSTE LIJN (BEGINLIJN VAN GEEXPOLDEERDE RETOUR-POLYLINE (=EERSTE IN ARRAY) TRIMMEN
        'TOT LAATSTE SNIJPUNT, REST VERWIJDEREN
        
        'VOOR 31 MAART 2003:
        If ArrHandle(t) = sLaatseHandle Then
        'MsgBox sLaatseHandle, vbInformation
        
        'If ArrHandle(t) = ArrHandle(1) Then
            '28 maar aangevuld alleen met volgende regel
            If element.EntityName = "AcDbLine" Then element.EndPoint = PsnijpuntPublic
            ' ** 21 MEI 2003, OMDAT VARIABELE NIET GOED WAS (VARIANT IPV DOUBLE-ARRAY)
            ' SPRONG HET PROGRAMMA HIER UIT DEZE SUB ? IS NU AANGEPAST.
            Exit For
        Else
            'MsgBox "13 mei 2004 erase teruggezet !"
            element.Color = acRed
            element.Erase
        End If
      
        
    Next t

End Sub




 '-------------------------------------------------------------
    'AFBEELDEN PUNT OP SNIJPUNT
    '-------------------------------------------------------------
    
'    Dim retCoord As Variant
'    retCoord = PlineObj.Coordinates
'
'    Dim X1, Y1, X2, Y2 As Double
'
'    Dim LijnstukTeller As Integer
'    For t = LBound(retCoord) To UBound(retCoord) - 2 Step 2
'
'        LijnstukTeller = LijnstukTeller + 1
'
'        X1 = retCoord(t)
'        Y1 = retCoord(t + 1)
'        X2 = retCoord(t + 2)
'        Y2 = retCoord(t + 3)
'
'        'Call TekenLijntje(X1, Y1, X2, Y2)
'
'        'MsgBox "X1=" & X1 & "     Y1=" & Y1 & Chr(10) & Chr(13) _
'            & "X2=" & X2 & "     Y2=" & Y2, , "lijnstuk: " & LijnstukTeller
'
'    Next t

Attribute VB_Name = "M_4BerekenKopStaartNW"


'***********************************************************
' NIEUW AANGEPAST DOOR EBR: 13 FEB 2003
'***********************************************************

Public Sub BerekenKopStaart1(Rollengte As Double)

    ' --------------------------------------------------------------
    ' VOORGAANDE LOGFILE VERWIJDEREN
    ' --------------------------------------------------------------

    Call VerwijderenLogFile

    SchrijfLogFile ("-------------------------------------------------------------------")
    SchrijfLogFile (Date & "      " & Time)
    SchrijfLogFile ("-------------------------------------------------------------------")
    SchrijfLogFile ("")
    SchrijfLogFile ("")
    
    ' --------------------------------------------------------------
    ' PLAATSEN UNDO-MARK
    ' --------------------------------------------------------------
    '7 APTIL 2003 NIEUW
    
    'ThisDrawing.StartUndoMark
    'DIT WERK NIET
    
    ThisDrawing.SetVariable "modemacro", "Rollengte=" & Round(Rollengte / 100, 1) & " m"
   
    
    ' --------------------------------------------------------------
    ' UITLEZEN RESERVE LENGTE (SNIT) (controle zie F_main)
    ' --------------------------------------------------------------
    
    On Error Resume Next
    Dim dSnit As Double
    dSnit = F_Main.TextBox1.Text
    dSnit = dSnit * 100
    SchrijfLogFile ("Reservelengte (snit) = " & dSnit & " cm")
    
    ' --------------------------------------------------------------
    ' NIEUWE ROLLENGTE (INCLUSIEF SNIT)
    ' --------------------------------------------------------------

    Rollengte = Rollengte - dSnit
    ' --------------------------------------------------------------
    ' FORMULIER VERBERGEN
    ' --------------------------------------------------------------
    
    
    F_Main.Hide

    ' --------------------------------------------------------------
    ' INVOEREN BEGINLENGTE (24 FEB 2003)
    ' --------------------------------------------------------------

    Dim dInvoerLengte As Double
    dInvoerLengte = Rollengte
      
    ' dInvoerLengte = InputBox("Vul de rollengte in:", "Invoer rollengte", "1000")
    
    SchrijfLogFile ("Ingevoerde lengte=" & dInvoerLengte)
    
    ' --------------------------------------------------------------
    ' NIEUWE LAAG AANMAKEN EN AKTIEF MAKEN
    ' --------------------------------------------------------------
    
    Call LaagAktief
    
    
    ' --------------------------------------------------------------
    ' SELECTEREN 1E GEDEELTE VAN DE AANVOERPOLYLINE (1 FEB 2004)
    ' aanvoer-polyline kan in twee stukken worden gesplits om rekenfouten
    ' bij complexe aanvoer-polyline te voorkomen.
    ' --------------------------------------------------------------
    
    If F_Main.CheckBox11.Value = True Then
        'MsgBox "Selecteer 1e gedeelte van de (gesplitste) aanvoerpolyline.", vbInformation, "Selecteer"
        
        Dim ReturnObj1a As Object
        On Error Resume Next
        Dim iFoutSelectieTeller As Integer
    
Opnieuw1a:
    
        If iFoutSelectieTeller > 1 Then End
        
        
        ThisDrawing.Utility.GetEntity ReturnObj1a, basePnt1, "Selecteer 1e gedeelte van de (gesplitste) aanvoerpolyline:"
        If Err <> 0 Then
            Err.Clear
            If iFoutSelectieTeller < 1 Then MsgBox "Verkeerde selectie", vbCritical, "Let op"
            iFoutSelectieTeller = iFoutSelectieTeller + 1
            GoTo Opnieuw1
            'Exit Sub
        End If
                
        If ReturnObj1a.EntityName <> "AcDbPolyline" Then
            MsgBox "Geen aanvoer-polyline geselecteerd: " & Right$(ReturnObj1a.EntityName, Len(ReturnObj1a.EntityName) - 4), vbCritical, "Let op"
            FoutSelectieTeller = iFoutSelectieTeller + 1
            GoTo Opnieuw1a
        End If
        
        iFoutSelectieTeller = 0
        
        ReturnObj1a.Color = acByLayer
        ReturnObj1a.Highlight (True)
        ReturnObj1a.Update
        
        
        'BEREKENEN LENGTE VAN GEBROKEN (BREAK) AANVOER-POLYLINE (EERSTE GEDEELTE)
        Dim dLengteAanvoerPolylineVanEersteGedeelte As Double
        dLengteAanvoerPolylineVanEersteGedeelte = LengtePolyline2(ReturnObj1a)
        
        ReturnObj1a.Layer = ThisDrawing.ActiveLayer.Name
        
        iFoutSelectieTeller = 0
        
        
        
         'MsgBox dLengteAanvoerPolylineVanEersteGedeelte
    
        dInvoerLengte = dInvoerLengte - dLengteAanvoerPolylineVanEersteGedeelte
    
        'MsgBox "dInvoerLengte= " & dInvoerLengte
        
        
        
    End If
    
    
    
    
   
    ' --------------------------------------------------------------
    ' SELECTEREN DE AANVOERPOLYLINE (1 FEB 2004)
    ' --------------------------------------------------------------
   
    
    
    Dim ReturnObj1 As Object
    On Error Resume Next
    'Dim iFoutSelectieTeller As Integer
    
Opnieuw1:
    
    If iFoutSelectieTeller > 1 Then End
    
    
    ThisDrawing.Utility.GetEntity ReturnObj1, basePnt1, "Selecteer de aanvoer-polyline."
    If Err <> 0 Then
        Err.Clear
        If iFoutSelectieTeller < 1 Then MsgBox "Verkeerde selectie", vbCritical, "Let op"
        iFoutSelectieTeller = iFoutSelectieTeller + 1
        GoTo Opnieuw1
        'Exit Sub
    End If
            
    If ReturnObj1.EntityName <> "AcDbPolyline" Then
        MsgBox "Geen aanvoer-polyline geselecteerd: " & Right$(ReturnObj1.EntityName, Len(ReturnObj1.EntityName) - 4), vbCritical, "Let op"
        FoutSelectieTeller = iFoutSelectieTeller + 1
        GoTo Opnieuw1
    End If
    
    iFoutSelectieTeller = 0
    
    ReturnObj1.Color = acByLayer
    
    Dim plineObj As AcadLWPolyline
    Set plineObj = ReturnObj1
    
    
    '1 feb 200: controle of polyline al is aangewezen (eerste gedeelte van gebroken aanvoer-poly):
    If F_Main.CheckBox11.Value = True Then
        If ReturnObj1a.handle = plineObj.handle Then
            MsgBox "Polyline is niet gesplitst: dezelfde aanvoer-polyline geselecteerd.", vbInformation, "Let op"
            End
        End If
    End If
    
    plineObj.Highlight (True)
    
    
    
    
''''''' >>> 13 MEI 2004 DEZE IETS LAGER GEPLAATST (NET NA TRIMMEN AANVOER-POLYLINE)
''''''    ' --------------------------------------------------------------
''''''    ' FILLET DE AANVOER POLYLINE (24 FEB 2003)
''''''    ' --------------------------------------------------------------
''''''
''''''    Set copyCircleObj = ReturnObj1.Copy()
''''''    ReturnObj1.Erase
''''''    ThisDrawing.SendCommand "_Fillet" & vbCr & "R" & vbCr & "5" & vbCr & "P" & vbCr & "L" & vbCr
''''''    ThisDrawing.Regen acAllViewports
''''''    Set plineObj = copyCircleObj
''''''    plineObj.Layer = ThisDrawing.ActiveLayer.Name
        
    
    
    ' --------------------------------------------------------------
    ' SELECTEREN RETOUR POLYLINE (24 MAART 2003)
    ' --------------------------------------------------------------
    
    
    Dim RetourPoly As Object
    Dim basePnt2 As Variant
    'On Error Resume Next
    
Opnieuw2:
    
    If iFoutSelectieTeller > 1 Then End
    
    ThisDrawing.Utility.GetEntity RetourPoly, basePnt2, "Selecteer de retour-polyline."
    
    If Err <> 0 Then
        Err.Clear
        If iFoutSelectieTeller < 1 Then MsgBox "Verkeerd geselecteerd", vbCritical, "Let op"
        iFoutSelectieTeller = iFoutSelectieTeller + 1
        GoTo Opnieuw2
        'Exit Sub
    End If
            
    If RetourPoly.EntityName <> "AcDbPolyline" Then
        If iFoutSelectieTeller < 1 Then MsgBox "Geen retour-polyline geselecteerd: " & Right$(RetourPoly.EntityName, Len(RetourPoly.EntityName) - 4), vbCritical, "Let op"
        iFoutSelectieTeller = iFoutSelectieTeller + 1
        GoTo Opnieuw2
        'Exit Sub
    End If
    
    iFoutSelectieTeller = 0
    
    RetourPoly.Color = acByLayer
    RetourPoly.Highlight (True)
     
    
   
   
    
    ' --------------------------------------------------------------
    ' SELECTEREN EERSTE LIJN (BEGIN VAN DE LEIDING)
    ' --------------------------------------------------------------
    
    Dim returnObj As Object
    'On Error Resume Next
    
Opnieuw3:
    
    If iFoutSelectieTeller > 1 Then End
    
    ThisDrawing.Utility.GetEntity returnObj, basePnt, "Selecteer het beginpunt van de eerste leiding (line)."
    
    If Err <> 0 Then
        Err.Clear
        If iFoutSelectieTeller < 1 Then MsgBox "Verkeerd geselecteerd", vbCritical, "Let op"
        iFoutSelectieTeller = iFoutSelectieTeller + 1
        GoTo Opnieuw3
    End If
            
    If returnObj.EntityName <> "AcDbLine" Then
        MsgBox "Geen lijn geselecteerd: " & Right$(returnObj.EntityName, Len(returnObj.EntityName) - 4)
        iFoutSelectieTeller = iFoutSelectieTeller + 1
        GoTo Opnieuw3
        'Exit Sub
    End If
    
    iFoutSelectieTeller = 0
        
    returnObj.Color = acByLayer
    returnObj.Update
    returnObj.Highlight True
    
     
    Dim dTotaleLengte As Double
    dTotaleLengte = returnObj.Length
    
    
    
    
    ' --------------------------------------------------------------
    ' BEPALEN SNIJPUNT VAN AANVOER-POLYLINE MET EERSTE LEIDING
    ' --------------------------------------------------------------
    
    Dim vSnijpunt As Variant
    vSnijpunt = BepalenVanSnijpunt(returnObj, plineObj, 3)
    'MsgBox vSnijpunt(0) & Chr(10) & Chr(13) & vSnijpunt(1), vbExclamation
    'Punt (vSnijpunt)
    
     
    
        
    
'''    6 AUG 2003 ONDERSTAANDE DEEL IS UITGEZET OMDAT BOVENSTAANDE FILLET-COMMANDO HIER VOOR IN DE
'''    PLAATS IS GEKOMEN.

    ' --------------------------------------------------------------
    ' TRIMMEN AANVOERPOLYLINE TOT SNIJPUNT MET EERSTE LEIDING (25 FEB 2003)
    ' --------------------------------------------------------------

    'INDIEN ER WEL EEN SNIJPUNT IS DAN:

    If vSnijpunt(0) = 0 And vSnijpunt(1) = 0 Then
        SchrijfLogFile ("aanvoer polyline heeft geen snijpunt met de eerste leiding (en zal niet worden getrimd).")

    Else
    
            'MsgBox "6 mei 2004, onderstaande uitgezet en nieuwe functie"
            
            Call TrimPolyline(plineObj, vSnijpunt)
''''        ONDERSTAANDE IS 6 MEI 2004 UITGEZET EN VERVANGEN DOOR NIEUWE FUNCTIE


''''        'OPVRAGEN BEGINPUNT VAN POLYLINE EN HIEROP PIJL PLAATSEN
''''        Dim coord As Variant    'vertex-array
''''        Dim varVert As Variant  'vertex
''''        Dim intVCnt As Integer  'vertex-counter
''''
''''        coord = plineObj.Coordinates
''''        'MsgBox coord(0) & ", " & coord(1)
''''
''''        For Each varVert In coord
''''            intVCnt = intVCnt + 1
''''        Next
''''
''''        'OPVRAGEN EINDPUNT LWT-POLYLINE
''''        'MsgBox "Laatste x =" & coord(intVCnt - 2)
''''        'MsgBox "Laatste y =" & coord(intVCnt - 1)
''''
''''        'nieuw array, want lwt-poly bestaat heeft geen z-coordinaat en snijpunt wel
''''        Dim NieuwEindpuntPoly(0 To 1) As Double
''''        NieuwEindpuntPoly(0) = vSnijpunt(0)
''''        NieuwEindpuntPoly(1) = vSnijpunt(1)
''''
''''        'LET OP: COORDINATE BESTAAT UIT TWEE VERTEXEN (X EN Y), COORDINATE IS EEN KNOOPPUNT.
''''        'DAAROM DELEN DOOR 2
''''        'EERSTE VERTEX BEGINT BIJ 0, DAAROM LAATSTE -1
''''
''''        plineObj.Coordinate(intVCnt / 2 - 1) = NieuwEindpuntPoly
''''        plineObj.Update

    End If
    
    ' --------------------------------------------------------------
    ' FILLET DE AANVOER POLYLINE (24 FEB 2003)
    ' --------------------------------------------------------------
    
    
    Set copyCircleObj = plineObj.Copy()
    ReturnObj1.Erase
    ThisDrawing.SendCommand "_Fillet" & vbCr & "R" & vbCr & "5" & vbCr & "P" & vbCr & "L" & vbCr
    ThisDrawing.Regen acAllViewports
    Set plineObj = copyCircleObj
    plineObj.Layer = ThisDrawing.ActiveLayer.Name
    
    
    ' --------------------------------------------------------------
    ' FILLET DE RETOUR POLYLINE (24 MAART 2003)
    ' --------------------------------------------------------------
    
    Set copyRetourPoly = RetourPoly.Copy()
    RetourPoly.Erase
    ThisDrawing.SendCommand "_Fillet" & vbCr & "R" & vbCr & "5" & vbCr & "P" & vbCr & "L" & vbCr
    ThisDrawing.Regen acAllViewports
    Set RetourPoly = copyRetourPoly
    
    RetourPoly.Layer = ThisDrawing.ActiveLayer.Name
    
           
    ' --------------------------------------------------------------
    ' OPVRAGEN LENGTE VAN AANVOER-POLYLINE (VAN GETRIMDE POLYLINE)
    ' --------------------------------------------------------------
    
    Dim dLengteAanvoerPolyline As Double
    dLengteAanvoerPolyline = LengtePolyline2(plineObj)
    
    If dLengteAanvoerPolyline > dInvoerLengte Then
        MsgBox "De lengte van de aanvoer-polyline tot het snijpunt (" & Round(dLengteAanvoerPolyline, 1) / 100 & " m) is groter dan de ingevoerde rollengte.", vbExclamation, "Let op"
        SchrijfLogFile ("De lengte van de aanvoer-polyline tot het snijpunt (" & Round(dLengteAanvoerPolyline, 1) / 100 & " m) is groter dan de ingevoerde rollengte.")
        End
    End If
    
    If 2 * dLengteAanvoerPolyline > dInvoerLengte Then
        MsgBox "Lengte van aanvoer- en retour-polyline > ingevoerde lengte (er kunnen geen slingers worden gemaakt.)", vbInformation
        SchrijfLogFile ("Lengte van aanvoer- + retour-polyline > ingevoerde lengte (er kunnen geen slingers worden gemaakt.")
        End
    End If
    
    'MsgBox "Totale lengte van aanvoer-polyline=" & dLengteAanvoerPolyline, vbInformation
    SchrijfLogFile ("lengte van aanvoer-polyline (tot snijp eerste leiding)=" & dLengteAanvoerPolyline)
        
    ' -----------------------------------------------------------------------
    ' GESELECTEERDE AANVOER-POLYLINE EN EERSTE LEIDING IN JUISTE LAYER PLAATSEN
    ' -----------------------------------------------------------------------
    
    plineObj.Layer = ThisDrawing.ActiveLayer.Name
    returnObj.Layer = ThisDrawing.ActiveLayer.Name
    
         
    ' -----------------------------------------------------------------------
    ' EXPLODEREN AANVOER-POLYLINE
    ' -----------------------------------------------------------------------
    
    ' *** NIEUW OP 19 MEI 2003
    'plineObj.Explode
    'plineObj.Delete
    
    ' -----------------------------------------------------------------------
    ' EXPLODEREN RETOUR-POLYLINE VAN GETRIMDE POLYLINE (NW 17 feb 2003)
    ' HIER WORDEN LOSSE LIJNEN OVERHEEN GETEKEND (IVM LENGTE BEREKENING)
    ' -----------------------------------------------------------------------
    
    'volgende 4 regels als test:
    'Dim PlineObj As AcadLWPolyline
    'Dim lijnobj As AcadLine
    'Set PlineObj = ThisDrawing.ModelSpace.Item(0)
    'Set lijnobj = ThisDrawing.ModelSpace.Item(1)

    'MsgBox "*** NIEUW 24 MAART 03"
    Call M_4BepalenLengteNEW.TekenLijnenOverPolyline(RetourPoly)

    '**** 26 FEB 2003 GETEST EN WERKT
    'Call M_BepalenLengteNEW.VerwijderenLosseLines
    
   
   
    ' --------------------------------------------------------------
    ' BEPALEN OF BEGIN OF EINDPUNT VAN DE LEIDING GESELECTEERD IS
    ' --------------------------------------------------------------
    
    Dim bStartpointGevonden As Boolean

    If Lengte(basePnt, returnObj.EndPoint) > Lengte(basePnt, returnObj.StartPoint) Then
        'MsgBox "Lijn aan beginzijde geselecteerd"
        bStartpointGevonden = False

        '180 DRAAIEN EERSTE (GESELECTEERDE) LEIDING (nieuw 20 mrt 2003, dit om berekening lijnlengtes e.d. te vereenvoudigen)
        Dim PnwBegin As Variant
        Dim PnwEind As Variant
        PnwBegin = returnObj.EndPoint
        PnwEind = returnObj.StartPoint
        returnObj.StartPoint = PnwBegin
        returnObj.EndPoint = PnwEind

        'MsgBox "Eerste leiding 180 graden geroteerd"
        bStartpointGevonden = True
        
    Else
        'MsgBox "Lijn aan eindzijde geselecteerd"
        bStartpointGevonden = True
    End If
    
    
    ' --------------------------------------------------------------------
    ' NIEUW 5 AUG 2003 FILLET AANVOERPOLYLINE MET 1E GESELECTEERDE LEIDING
    ' --------------------------------------------------------------------
    'MsgBox "5 AUG FILLET, TOT HIER"
    
    Dim coord1 As Variant    'vertex-array
    Dim varVert1 As Variant  'vertex
    Dim intVCnt1 As Integer  'vertex-counter

    coord1 = plineObj.Coordinates
    'MsgBox coord(0) & ", " & coord(1)

    For Each varVert1 In coord1
        intVCnt1 = intVCnt1 + 1
    Next

    'OPVRAGEN EEN NA LAATSTE EINDPUNT LWT-POLYLINE
    'MsgBox "Laatste x =" & coord(intVCnt - 4)
    'MsgBox "Laatste y =" & coord(intVCnt - 3)
    
    Dim FilletP1(0 To 2) As Double
    FilletP1(0) = coord1(intVCnt1 - 4)    'EEN NA LAATSTE X-COORD
    FilletP1(1) = coord1(intVCnt1 - 3)    'EEN NA LAATSTE Y-COORD
    
    'Punt (FilletP1)
    
    
   
    
    Dim Psnij1 As Variant
    'let op, gebruik acextendthisentity, anders bij moeilijke aanvoerpolylines fout!
    Psnij1 = returnObj.IntersectWith(plineObj, acExtendThisEntity)
    'MsgBox Psnij1(0) & "  " & Psnij1(1)
    
    If IsEmpty(Psnij1) Then
        MsgBox "Geen snijpunt gevonden. Afronding bij eerste leiding met aanvoerpolyline kan niet worden gemaakt", vbInformation, " Let op"
        
    Else
        
        Call M_6Fillet.Fillet5aug(FilletP1, returnObj.StartPoint, Psnij1, 5)
       
        
        Dim FilletArcObj As AcadEntity
        Set FilletArcObj = ThisDrawing.ModelSpace.Item(ThisDrawing.ModelSpace.Count - 1)
        
        
        If FilletArcObj.EntityName <> "AcDbArc" Then
            MsgBox "Afronding bij aanvoerleiding is niet gelukt.", vbInformation, "Let op"
        Else
            'onthouden oorspronkelijke hoek van geselecteerde leiding, ter controle
            Dim dHoekvanreturnObj As Double
            dHoekvanreturnObj = returnObj.Angle
            
        
            Dim dEindpuntFilletArc As Variant
            'wijzigen eindpunt (lees beginpunt) van geselecteerde lijn op eindpunt van fillet-arc.
            
            'onthouden originele eindpunt van geselecteerde leiding
            Dim dOrgReturnObjStartPoint As Variant
            dOrgReturnObjStartPoint = returnObj.StartPoint
            
            returnObj.EndPoint = FilletArcObj.EndPoint
            dEindpuntFilletArc = FilletArcObj.StartPoint
            
            
            'controleren of juiste punt van arc gekozen is, anders punt omkeren
            If Round(dHoekvanreturnObj, 4) <> Round(returnObj.Angle, 4) Then

                'lijnen terugzetten
                returnObj.EndPoint = dOrgReturnObjStartPoint

                'nu tegen andere arc-uiteinde plaatsen
                returnObj.EndPoint = FilletArcObj.StartPoint
                dEindpuntFilletArc = FilletArcObj.EndPoint
            End If

            'laatste punt van aanvoer-polyline wijzigen
            Dim NieuwEindpuntPoly1(0 To 1) As Double
            NieuwEindpuntPoly1(0) = dEindpuntFilletArc(0)
            NieuwEindpuntPoly1(1) = dEindpuntFilletArc(1)
            plineObj.Coordinate(intVCnt1 / 2 - 1) = NieuwEindpuntPoly1
            plineObj.Update

            
        
        End If
    End If
    
    
    ' -----------------------------------------------------------------------
    ' EXPLODEREN AANVOER-POLYLINE
    ' -----------------------------------------------------------------------
    
    ' *** NIEUW OP 19 MEI 2003, VERPLAATST OP 6 AUG 2003 (KOMT VAN BOVEN)
    
    plineObj.Explode
    plineObj.Delete
    
    ' --------------------------------------------------------------------------
    ' GESELECTEERDE LINE VERLENGEN TOT HET SNIJPUNT MET DE AANVOER-POLYLINE
    ' INDIEN ER EEN SNIJPUNT IS.
    ' --------------------------------------------------------------------------
    'GEHEEL NIEUW 26 MAART 2003
    '***UITGEZET OP 6 AUG 2003
    
'    If vSnijpunt(0) <> 0 And vSnijpunt(1) <> 0 Then
'        'LIJN IS 180 GEDRAAID !
'        returnObj.EndPoint = vSnijpunt
'    End If
    
    
    ' --------------------------------------------------------------
    ' ALLE VOORGAANDE SELECTIESETS VERWIJDEREN
    ' --------------------------------------------------------------
    
    Call SelectiesetsVerwijderen
   
    
    ' --------------------------------------------------------------
    ' BEREKENEN WELKE LIJNEN MET ELKAAR VERBONDEN ZIJN
    ' --------------------------------------------------------------
   
    
    Dim ReturnEindpunt As Variant
    
    Dim element As Object
    Dim Beginpunt As Variant
    Dim Eindpunt As Variant
    Dim LijnGevonden As Boolean
    Dim StartpuntGevonden As Boolean
    Dim testobj As Object
    Dim bMeerdereLijnenGevonden As Boolean
    
    
    Dim p1(0 To 2) As Double
    Dim p2(0 To 2) As Double
    'Dim ssetObj As AcadSelectionSet
    Dim LijnTeller As Integer
    Dim gpCode(0) As Integer
    Dim dataValue(0) As Variant
    Dim groupCode As Variant, dataCode As Variant
    Dim mode As Integer
    
    Dim RollengteVerschil As Double
    
    Dim VoorgaandeElement As Object
    Dim VoorVoorgaandeElement As Object
    Dim bVoorVoorgaandeElement_Aanwezig As Boolean
    Dim PSnijpVoorgaande As Variant
    
    
    Dim VorigeHandle As String
    VorigeHandle = returnObj.handle
    Dim t As Integer
    
    Dim VoorgaandeArcBeginpuntGevonden As Boolean
    
    ZoomAll
    
    
    
    
    ' -------------------------------------------------------------------------------------------------
    ' *** 27 MEI 2003: INSTELLEN LIMITS OFF.
    ' LET OP, INDIEN LIMITS ZEER GROOT INGESTELD STAAN DAN GAAT BEREKENING
    ' KOP-STAAT NIET GOED: MAAK LIMITS KLEINER (GELIJK AAN EXTENTS OF MAX 5X GROTER BIJVOORBEELD)
    ' -------------------------------------------------------------------------------------------------
     
    Dim dLimMin As Variant
    Dim dLimMax As Variant
    dLimMin = ThisDrawing.GetVariable("LIMMIN")
    dLimMax = ThisDrawing.GetVariable("LIMMAX")
    
    Dim dExtMin As Variant
    Dim dExtMax As Variant
    dExtMin = ThisDrawing.GetVariable("EXTMIN")
    dExtMax = ThisDrawing.GetVariable("EXTMAX")
    
    Dim bControleerLimits As Boolean
    If dLimMin(0) / dExtMin(0) > 5 Then bControleerLimits = True
    If dLimMin(1) / dExtMin(1) > 5 Then bControleerLimits = True
    
    If dLimMax(0) / dExtMax(0) > 5 Then bControleerLimits = True
    If dLimMax(1) / dExtMax(1) > 5 Then bControleerLimits = True
    
    If bControleerLimits = True Then MsgBox "Limits staan zeer groot (5x Extents) ingesteld t.o.v. tekening-extents." _
    & Chr(10) & Chr(13) & "Stel limits goed in om rekenfouten te voorkomen.", vbCritical, "Limits niet juist"
    'deze op 31 jan 2004 uitgezet (dus toch doorgaan met berekenen)
    'End
    
'    Dim currLimits As Variant
'    currLimits = ThisDrawing.Limits
'
'
    ThisDrawing.SetVariable "LIMCHECK", 0      'limits off
    
    
'    ThisDrawing.Limits = currLimits
'    ThisDrawing.Regen (acActiveViewport)
    
    
   
    
    
    
    '***************************************************************************************************
    '********************   START HOOFSROUTINE  ********************************************************
    '***************************************************************************************************


    
opnieuw:

    t = t + 1
    
    'On Error Resume Next
    ' VOORGAAND OBJECT AANMAKEN, BEHALVE DE EERSTE KEER
    If t > 1 Then
        Set VoorVoorgaandeElement = VoorgaandeElement
        'If Err Then Err.Clear
        bVoorVoorgaandeElement_Aanwezig = True
        PSnijpVoorgaande = PsnijpuntPublic
    Else
        bVoorVoorgaandeElement_Aanwezig = False
        PSnijpVoorgaande = vSnijpunt
    End If
    
    'MsgBox vSnijpunt(0) & Chr(10) & Chr(13) & vSnijpunt(1) & Chr(10) & Chr(13) & vSnijpunt(2)
    
    
   
    
    Set VoorgaandeElement = returnObj
    'If Err Then Err.Clear
    
    

    ' MsgBox "VoorgaandeElement=" & VoorgaandeElement.handle & Chr(10) & Chr(13) & "VoorVoorgaandeElement=" & VoorVoorgaandeElement.handle
   

    


    If bStartpointGevonden = True Then
        ReturnEindpunt = returnObj.StartPoint
    Else
        ReturnEindpunt = returnObj.EndPoint
    End If
    

    LijnGevonden = False
    LijnTeller = 0
    
    '---------------------------------------------------
    'Aanmaken selectieset
    '---------------------------------------------------
    'voor 31 maart, was 0.1 (programma stopte)
   
    p1(0) = ReturnEindpunt(0) - 0.3
    p1(1) = ReturnEindpunt(1) - 0.3
    p1(2) = 0
    p2(0) = ReturnEindpunt(0) + 0.3
    p2(1) = ReturnEindpunt(1) + 0.3
    p2(2) = 0
        
    Set ssetObj = ThisDrawing.SelectionSets.Add("SSET")
    If Err Then ssetObj.Clear
    mode = acSelectionSetCrossing
    ssetObj.Select mode, p2, p1
    
    If Err Then MsgBox Err.Description, vbInformation, "FOUT 0"
    
    For Each element In ssetObj
        'MsgBox element.handle
        If element.handle <> VorigeHandle Then
            If element.EntityName = "AcDbLine" Or element.EntityName = "AcDbArc" Then
                '*** Nieuw 25 maart 2003
                'MsgBox Element.Layer & "   " & ThisDrawing.ActiveLayer.Name
                
                'ORIGINEEL VOOR 7 APRIL 2003
                'If element.Layer <> ThisDrawing.ActiveLayer.Name Then
                
                'NIEUW 7 APRIL 2003
                If UCase(element.Layer) = "LEGPLAN" Then
                
                    element.Highlight True
                    LijnTeller = LijnTeller + 1
                    Set returnObj = element
                    
                    '*** MsgBox returnObj.handle, , LijnTeller
                
                    returnObj.Layer = ThisDrawing.ActiveLayer.Name
                    returnObj.Color = acByLayer
                    
                End If
            End If
        End If
    Next element
    
    'MsgBox returnObj.handle
    
    If Err Then MsgBox Err.Description, vbInformation, "FOUT 1"
    
    ssetObj.Clear
    ssetObj.Delete
    
    If Err Then MsgBox Err.Description, vbInformation, "FOUT 2"
    
   
     
   
    
    
    If LijnTeller = 0 Then
        ZoomPrevious
        MsgBox "Totale berekende lengte = " & Round(dTotaleLengte / 100, 1) & " m" _
        & Chr(10) & Chr(13) & "(dus korter dan ingevoerde rollengte: retour-polyline handmatig afmaken (explode).", vbInformation, "Einde"
        Exit Sub
        
        
''''        UITBREIDING 21 MEI 2004: SELECTIE VAN ARC OF LINE ALS ER EEN OPENING IS EN KOP
''''        STAART NIET GEVONDEN KAN WORDEN. TOCH WEER UITGEZET: COMPLEX !

'''''        Dim SelectieObj As AcadEntity
'''''        Dim Pp As Variant
'''''        ThisDrawing.Utility.GetEntity SelectieObj, Pp
'''''        Set returnObj = SelectieObj
'''''
'''''        If Err Then MsgBox Err.Description
'''''
'''''        element.Highlight True
'''''        LijnTeller = LijnTeller + 1
'''''
'''''        returnObj.Layer = ThisDrawing.ActiveLayer.Name
'''''        returnObj.Color = acByLayer
        
        
       
        
        'Exit Sub
    End If
    
    
    'origineel:
    'If LijnTeller > 1 Then ZoomPrevious: MsgBox "Meerdere lijnen gevonden   ': Einde": End
    
    'aangepast op 25 mrt 2003
    'MsgBox "tot hier 25 mrt 2003"
    '31 maart 2003 aangepast
    If LijnTeller > 1 Then
        ZoomPrevious
        SchrijfLogFile ("Meerdere lijnen gevonden.")
        'MsgBox "Meerdere lijnen gevonden   ': Einde"
        'End        'doorgaan
    End If
    
     
    '---------------------------------------------------
    ' BEPALEN TOTALE LENGTE
    '---------------------------------------------------
    
    If returnObj.EntityName = "AcDbLine" Then
        dTotaleLengte = dTotaleLengte + returnObj.Length
        Debug.Print returnObj.Length & "            " & dTotaleLengte
    Else
        dTotaleLengte = dTotaleLengte + returnObj.ArcLength
        Debug.Print returnObj.ArcLength & "            " & dTotaleLengte
    End If
    
    
    '---------------------------------------------------
    ' BEPALEN BEGIN OF EINPUNT
    '---------------------------------------------------
    
    If Lengte(ReturnEindpunt, returnObj.EndPoint) > Lengte(ReturnEindpunt, returnObj.StartPoint) Then
       ' MsgBox "Lijn aan beginzijde geselecteerd"
        bStartpointGevonden = False
    Else
       ' MsgBox "Lijn aan eindzijde geselecteerd"
        bStartpointGevonden = True
    End If
    
    VorigeHandle = returnObj.handle
    
        
    '------------------------------------------------------------
    ' BEPALEN OF VAN ARC HET BEGIN- OF EINDPUNT GEVONDEN IS
    ' 30 MAART 2003 NIEUW
    '------------------------------------------------------------
    
    If returnObj.EntityName = "AcDbArc" Then
        VoorgaandeArcBeginpuntGevonden = bStartpointGevonden
    End If
    
    '*******************************************************
    ' BEREKENEN LENGTE TOT SNIJPUNT POLYLINE NIEUW 17 FEB 2003
    '*******************************************************
    Dim Debugmode As Boolean
    Debugmode = False
    
    If returnObj.EntityName <> "AcDbArc" Then
    
        If bStartpointGevonden = False Then
            'MsgBox "Laatste lijn roteren met 180 graden, (dan is het eindpunt altijd juist)."
            Dim PStartOrgineel As Variant
            Dim PEindOrgineel As Variant
            PStartOrgineel = returnObj.StartPoint
            PEindOrgineel = returnObj.EndPoint
            returnObj.StartPoint = PEindOrgineel
            returnObj.EndPoint = PStartOrgineel
            
            bStartpointGevonden = True
        End If
        
        lengtevanpoly = M_4BepalenLengteNEW.BepalenSnijpunt(RetourPoly, returnObj)
        
       
        'MsgBox "lengtevanpoly (retour-poly tot snijpunt)= " & lengtevanpoly & Chr(10) & Chr(13) _
        & "lengte van aanvoer poly= " & dLengteAanvoerPolyline & Chr(10) & Chr(13) _
        & "dTotaleLengte (losse lines en arcs)= " & dTotaleLengte & Chr(10) & Chr(13) _
        & Chr(10) & Chr(13) _
        & "totaal = " & lengtevanpoly + dLengteAanvoerPolyline + dTotaleLengte
         
        SchrijfLogFile ("dLengteAanvoerPolyline=" & Round(dLengteAanvoerPolyline, 1) & "        lengtevanpoly=" & Round(lengtevanpoly, 1) & "         dTotaleLengte=" & Round(dTotaleLengte, 1) & "      >>> " & Round(dLengteAanvoerPolyline + lengtevanpoly + dTotaleLengte, 1))
    
         
        'LET OP: SNIT IS AL IN INGEVOERDE ROLLENGTE VERWERKT
        If (dLengteAanvoerPolyline + lengtevanpoly + dTotaleLengte) > (dInvoerLengte) Then
        
        
        
        
        
       
        
        
        
        
        
' ***************************************************************************************************
' *** EINDE LENGTE-BEREKENING
' ***************************************************************************************************


            ' MsgBox "bVoorVoorgaandeElement_Aanwezig=" & bVoorVoorgaandeElement_Aanwezig


            'VERWIJDEREN RETOUR-POLYLINE
            RetourPoly.Delete
                         
            RollengteVerschil = dInvoerLengte - (dLengteAanvoerPolyline + lengtevanpoly + dTotaleLengte)
            'MsgBox "rollengte behaald ! Verschil = " & RollengteVerschil
            SchrijfLogFile ("rollengte behaald ! Verschil = " & RollengteVerschil)
            
            
            Application.Update
            
            
            'WEERGEVEN LENGTE-VERSCHIL
            If F_Main.CheckBox1.Value = True Then
                MsgBox "Rollengte: " & (dInvoerLengte) / 100 & " m" & Chr(10) & Chr(13) _
                    & "Reserve lengte: " & dSnit / 100 & " m" & Chr(10) & Chr(13) _
                    & Chr(10) & Chr(13) _
                    & "Lengte verschil: " & Abs(Round(RollengteVerschil, 0)) / 100 & " m", vbInformation, "Lengte verschil"
            End If
                    
            
            
            'lossen lines en arcs die over polyline getekend waren weer verwijderen (26 FEB 2003)
            Call M_4BepalenLengteNEW.VerwijderenLosseLines
            
 

            Dim Situatie As Integer
            Dim Peind As Variant
            Dim Pstart As Variant
            
            'Punt (PsnijpuntPublic)
            'Punt (returnObj.EndPoint)
            'PsnijpuntPublic = snijpunt leiding (returnobj) met aanvoer polyline
            'Psnijpunt = snijpunt van de eerste (geselecteerde) leiding met (geselecteerde) aanvoerpolyline
            
            SchrijfLogFile ("")
            
            If Lengte(PsnijpuntPublic, returnObj.StartPoint) > Lengte(PsnijpuntPublic, returnObj.EndPoint) Then
                SchrijfLogFile ("*SITUATIE 2    (volgende lijn doet ook mee in lengte berekening)")
                Situatie = 2
                'DEZE SITUATIE NOG BETER BEKIJKEN (LIMCHECK ?? EBR 21 MEI)
            Else
                SchrijfLogFile ("*SITUATIE 1    (voorgaande lijn doet mee in lengte berekening)")
                Situatie = 1
            End If




'*****************************************************************************************************************
''''            returnObj.Color = acGreen               'het laatste element
''''            VoorgaandeElement.Color = acMagenta     'de arc
''''            VoorVoorgaandeElement.Color = acRed     'de voorlaatste lijn
'*****************************************************************************************************************

            
            'MsgBox "returnObj.Length=" & returnObj.Length
            'MsgBox "RollengteVerschil=" & RollengteVerschil
                    
                   
            Dim dDraaipunt As Variant
            Dim dDraaiHoek As Variant
            
            Peind = returnObj.EndPoint
            Pstart = returnObj.StartPoint
                
            If Situatie = 1 Then
                    
                    If Peind(0) < PsnijpuntPublic(0) Then
                        If Debugmode Then MsgBox "SITUATIE 1 [A]:Snijp ligt (links) NEE RECHTS ! 28 MRT 2003, vbExclamation"
                        SchrijfLogFile ("SITUATIE 1 [A]")
                        F_Main.Label25.Caption = "SITUATIE 1 [A]"
                        
                        
                        'laatste lijn draaien en verkorten:
                        Call LijnlengteWijzigen(returnObj, returnObj.Length - (Abs(RollengteVerschil) / 2), True)
                        'InsertBlock "pijl", returnObj.EndPoint, "0"
                                               
                        'de voorlaatste lijn draaien inkorten
                        Call LijnlengteWijzigen(VoorVoorgaandeElement, VoorVoorgaandeElement.Length - (Abs(RollengteVerschil)) / 2, False)
                        
                        'de arc verplaatsen
                        VoorgaandeElement.Move VoorgaandeElement.StartPoint, returnObj.EndPoint      'dus startpoint
                    Else
                        If Debugmode Then MsgBox "SITUATIE 1 [B] Snijp ligt (rechts) NEE LINKS ! 28 MRT 2003, vbExclamation"
                        SchrijfLogFile ("SITUATIE 1 [B]")
                        F_Main.Label25.Caption = "SITUATIE 1 [B]"
                        
                        'GESPIEGELD T.O.V. BOVENSTAANDE SITUATIE
                        
                        'laatste lijn draaien en verkorten
                        Call LijnlengteWijzigen(returnObj, returnObj.Length - (Abs(RollengteVerschil) / 2), True)
                        
                        'de voorlaatste lijn draaien inkorten
                        Call LijnlengteWijzigen(VoorVoorgaandeElement, VoorVoorgaandeElement.Length - (Abs(RollengteVerschil)) / 2, False)
                        
                        'MsgBox "TOT HIER", vbExclamation
                        
                        'de arc verplaatsen
                        VoorgaandeElement.Move VoorgaandeElement.EndPoint, returnObj.EndPoint      'dus startpoint
                       
                    End If
                    
                    'EINDE PROGRAMMA
                    ThisDrawing.SetVariable "LIMCHECK", 0      'limits off, 27 MEI 2003
                    ZoomPrevious
                    Exit Sub
            End If
                                
' ***************************************************************************************************
                    
            
            If Situatie = 2 Then
            
                    Dim ArcCopyObj As AcadArc
                    'nieuw 30 maart 2003
                    Dim PbeginLaatsteLijn As Variant
                    PbeginLaatsteLijn = returnObj.StartPoint
                    
                    If Round(Peind(0), 0) < Round(PsnijpuntPublic(0), 0) Then
                            SchrijfLogFile ("SITUATIE 2 [A]")
                            F_Main.Label25.Caption = "SITUATIE 2 [A]"
                            'MsgBox "SITUATIE 2 [C], NOG BEKIJKEN, Snijp ligt RECHTS NEE LINKS !!!, hier gebelevden op 28 maart om 17:26 !", vbExclamation
                            
                                                                           
                            
                            'laatste lijn draaien en verkorten
                            Call LijnlengteWijzigen(returnObj, (returnObj.Length - Abs(RollengteVerschil)) / 2, False)
                            
                            
                            'de arc kopieren en roteren
                            Set ArcCopyObj = VoorgaandeElement.Copy()    'dus startpoint
                            ArcCopyObj.Rotate ArcCopyObj.StartPoint, 3.141592
                            
                            'ORIGINEEL VOOR 30 MAART
                            'ArcCopyObj.Move ArcCopyObj.EndPoint, returnObj.StartPoint
                             
                            'NIEUW 30 MA
                            'de arc veplaatsen
                            If VoorgaandeArcBeginpuntGevonden = bStartpointGevonden Then
                                ArcCopyObj.Move ArcCopyObj.StartPoint, returnObj.StartPoint
                            Else
                                ArcCopyObj.Move ArcCopyObj.EndPoint, returnObj.StartPoint
                            End If
                    
                    ElseIf Round(Peind(0), 0) > Round(PsnijpuntPublic(0), 0) Then
                            'MsgBox "SITUATIE 2 [B]:Snijp ligt LINKS TOT."
                            SchrijfLogFile ("SITUATIE 2 [B]")
                            F_Main.Label25.Caption = "SITUATIE 2 [B]"
                            
                            
                            
                            'laatste lijn draaien en verkorten
                            Call LijnlengteWijzigen(returnObj, (returnObj.Length - Abs(RollengteVerschil)) / 2, False)
                                                   
                            'de arc kopieren en roteren
                            Set ArcCopyObj = VoorgaandeElement.Copy()    'dus startpoint
                            ArcCopyObj.Rotate ArcCopyObj.EndPoint, 3.141592
                             
                            'ORIGINEEL VOOR 30 MAART
                            'ArcCopyObj.Move ArcCopyObj.EndPoint, returnObj.StartPoint
                             
                            'NIEUW 30 MAART
                            'de arc veplaatsen
                            If VoorgaandeArcBeginpuntGevonden = bStartpointGevonden Then
                                ArcCopyObj.Move ArcCopyObj.StartPoint, returnObj.StartPoint
                            Else
                                ArcCopyObj.Move ArcCopyObj.EndPoint, returnObj.StartPoint
                            End If
                            
                            'NIEUWE LIJN TEKENEN
                            'UITGEZET 7 AUG 2003: Call Punt1(PeindLaatsteLijn, acMagenta)
                            'UITGEZET 7 AUG 2003: Call Punt1(returnObj.StartPoint, acGreen)
                            
                            
                            '*** TOT HIER GEBLEVEN OP 30 MAART 2003 !!
                            'UITGEZET 7 AUG 2003:  Call TekenLijn(returnObj.StartPoint, PbeginLaatsteLijn, "0")
                            'Call LijnlengteWijzigen(returnObj, (returnObj.Length - Abs(RollengteVerschil)) / 2, False)
                    Else
                        SchrijfLogFile ("SITUATIE 3 !!")
                        F_Main.Label25.Caption = "SITUATIE 3 !!"
                        MsgBox "SITUATIE 3 !! (21 mei 2004, controle Ebr)", vbInformation
                        
                        'MsgBox "SITUATIE 3: Snijpunt is eindpunt lijn ! Einde", vbCritical
                        ''UITGEZET 7 AUG 2003: MsgBox "SITUATIE 2 [C], NOG BEKIJKEN, Snijp ligt RECHTS NEE LINKS !!!, hier gebelevden op 28 maart om 17:26 !", vbExclamation
                                                                   
                        
                        'laatste lijn draaien en verkorten
                        Call LijnlengteWijzigen(returnObj, (returnObj.Length - Abs(RollengteVerschil)) / 2, False)
                                                
                        'de arc kopieren en roteren
                        Set ArcCopyObj = VoorgaandeElement.Copy()    'dus startpoint
                        ArcCopyObj.Rotate ArcCopyObj.StartPoint, 3.141592
                        
                        'ORIGINEEL VOOR 30 MAART
                        'ArcCopyObj.Move ArcCopyObj.EndPoint, returnObj.StartPoint
                         
                        'NIEUW 30 MA
                        'de arc veplaatsen
                        If VoorgaandeArcBeginpuntGevonden = bStartpointGevonden Then
                            ArcCopyObj.Move ArcCopyObj.StartPoint, returnObj.StartPoint
                        Else
                            ArcCopyObj.Move ArcCopyObj.EndPoint, returnObj.StartPoint
                        End If
        
                    End If
                    
                    

                    'EINDE PROGRAMMA
                    '21 MEI 2004, ONDERSTAANDE REGEL ER BIJGEZET (KOPIE UIT SITUATIE 1)
                    ThisDrawing.SetVariable "LIMCHECK", 0      'limits off, 27 MEI 2003
                    
                    ZoomPrevious
                    Exit Sub
                    
                
            End If
            
            
' ***************************************************************************************************
' ***************************************************************************************************
' ***************************************************************************************************

             
        End If
        
       
    End If
    
    
    GoTo opnieuw
    

End Sub

Attribute VB_Name = "M_4LaagAktief"
Public Sub LaagAktief()

    '*** 19 mei 2003 routine geheel aangepast: nu > 99 groep_lagen mogelijk

    ' ------------------------------------------------------------------------------
    ' DEZE ROUTINE MAAK EEN NIEUWE LAAG AAN MET EEN JUISTE GROEPSNUMMER
    ' ------------------------------------------------------------------------------
    

    ' ------------------------------------------------------------------------------
    ' BEPALEN LAATSTE GROEP-NUMMER (UIT LAYERS)
    ' ------------------------------------------------------------------------------
    
    SchrijfLogFile ("BEPALEN LAATSTE GROEP-NUMMER (UIT LAYER)EN AANMAKEN NIEUWE LAYER")

    Dim LaagObj As AcadLayer
    Dim sLaagNaam As String
    Dim sLaagNummer As String
    Dim iLaagNummer As String
    Dim iHoogsteNummer As Integer
    'Dim sNwLaagnaam As String
    'Dim bGroepLaagBestaat As Boolean
    Dim sHoogsteGroepNaam As String

    For Each LaagObj In ThisDrawing.Layers
        sLaagNaam = UCase(LaagObj.Name)
        If Left$(sLaagNaam, 6) = "GROEP_" Then
        
            bGroepLaagBestaat = True

            sLaagNummer = Right(sLaagNaam, Len(sLaagNaam) - 6)
            If Val(sLaagNummer) <> sLaagNummer Then
                MsgBox "Laag " & sLaagNummer & " bevat een verkeerd nummer.", vbCritical, "Let op"
                End
            Else
                iLaagNummer = sLaagNummer
                If iLaagNummer > iHoogsteNummer Then iHoogsteNummer = iLaagNummer: sHoogsteGroepNaam = LaagObj.Name
            End If

        End If
    Next LaagObj
        
    
    
    ' ------------------------------------------------------------------------------
    ' ALS ER NOG GEEN GROEPSLAAG IS, DAN DEZE AANMAKEN EN EXIT SUB
    ' ------------------------------------------------------------------------------
      
    
    If sHoogsteGroepNaam = "" Then
        Call AanmakenLaag("groep_01", acCyan, True)
        Exit Sub
    End If
    
        
    
    ' ------------------------------------------------------------------------------
    ' BEPALEN OF ER ELEMENTEN IN DE HOOGSTE (LAATSTE)GROEPSLAAG STAAN
    ' ZO NIET, DAN GEEN NIEUWE LAAG AANMAKEN MAAR LAAG WEL AKTIEF MAKEN !
    ' ------------------------------------------------------------------------------
    
    'MsgBox sHoogsteGroepNaam
    
    Dim element As AcadEntity
    Dim bElementenGevonden As Boolean
    Dim LaatsteGroepLaagnaam As String
    
    For Each element In ThisDrawing.ModelSpace
        If element.Layer = sHoogsteGroepNaam Then
            bElementenGevonden = True
        End If
    Next element
        
    If bElementenGevonden <> True Then
        If ThisDrawing.Layers.Item(sHoogsteGroepNaam).Freeze = True Then ThisDrawing.Layers.Item(sHoogsteGroepNaam).Freeze = False
        ThisDrawing.Layers.Item(sHoogsteGroepNaam).LayerOn = True
        ThisDrawing.ActiveLayer = ThisDrawing.Layers.Item(sHoogsteGroepNaam)
        Exit Sub
    End If
    
    
    
    ' ------------------------------------------------------------------------------
    ' NIEUWE GROEPS-LAAG AANMAKEN (MET HOGER NUMMER)
    ' ------------------------------------------------------------------------------
    
    'MsgBox sHoogsteGroepNaam
    
    Dim pos As Integer
    Dim sGroepsnummer As String
    Dim iGroepsnummer As Integer
    
    sGroepsnummer = Right$(sHoogsteGroepNaam, Len(sHoogsteGroepNaam) - 6)
    sGroepsnummer = Trim(sGroepsnummer)
    
    If sGroepsnummer <> Val(sGroepsnummer) Then MsgBox "Verkeerd groepnummer in laag " & sHoogsteGroepNaam, vbCriticalm, "Let op": End
    
    iGroepsnummer = Val(sGroepsnummer)
    iGroepsnummer = iGroepsnummer + 1
    
    
    Dim sNieuweLaagNaam As String
    
    If iGroepsnummer < 10 Then
        sNieuweLaagNaam = "groep_0" & iGroepsnummer
    Else
        sNieuweLaagNaam = "groep_" & iGroepsnummer
    End If
    
    
    'MsgBox sNieuweLaagNaam
    
    ' ------------------------------------------------------------------------------
    ' LAAG KLEUR BEPALEN
    ' ------------------------------------------------------------------------------
    
    Dim KleurNo As Integer
    
    On Error Resume Next
    KleurNo = ThisDrawing.Layers.Item(sHoogsteGroepNaam).Color
    If Err Then Err.Clear
    'ER BESTAAT NOG GEEN LAAG GROEP-....

    If KleurNo = acGreen Then
        KleurNo = acCyan
    Else
        KleurNo = acGreen
    End If

    
    ' ------------------------------------------------------------------------------
    ' LAAG AANMAKEN EN AKTIEF ZETTEN
    ' ------------------------------------------------------------------------------
    
    Call AanmakenLaag(sNieuweLaagNaam, KleurNo, True)
   


    

  

End Sub

Attribute VB_Name = "M_5BerekenLengteInLayers"
Public Sub BerekenLengteInColors()

        F_Main.Hide

        Dim RetourObj As Object
        On Error Resume Next
        ThisDrawing.Utility.GetEntity RetourObj, basePnt, "Selecteer van welke kleur en laag de lengte berekend moet worden"
       
        If Err <> 0 Then
            Err.Clear
            'MsgBox "Verkeerd geselecteerd"
            Exit Sub
        End If
        
        RetourObj.Highlight (True)
        
        Dim element As Object
        Dim Lengte As Double
        Dim VerkeerdeObject As Boolean
        
        For Each element In ThisDrawing.ModelSpace
            If element.Color = RetourObj.Color Then
            If element.Layer = RetourObj.Layer Then
            
                    Select Case element.EntityName
                    Case "AcDbLine"
                        Lengte = Lengte + element.Length
                        element.Highlight True
                    Case "AcDbArc"
                        Lengte = Lengte + element.ArcLength
                        element.Highlight True
                    Case "AcDbPolyline"
                        Lengte = Lengte + LengtePolyline2(element)
                        element.Highlight True
                    Case Else
                        VerkeerdeObject = True
                        
                        'nieuw op 26 maart 2003
                        'circle plaatsen om verkeerde element, boundingbox om midden te bepalen
                        Dim minExt As Variant
                        Dim maxExt As Variant
                        element.GetBoundingBox minExt, maxExt
                        Dim Pcenter(0 To 2) As Double
                        Pcenter(0) = (minExt(0) + maxExt(0)) / 2
                        Pcenter(1) = (minExt(1) + maxExt(1)) / 2
                        Dim circleObj As AcadCircle
                        Set circleObj = ThisDrawing.ModelSpace.AddCircle(Pcenter, 60)
                        circleObj.Color = acRed
                        circleObj.Lineweight = acLnWt050
                        ThisDrawing.Preferences.LineWeightDisplay = True
                        
                    End Select
            End If
            End If
        Next element
        
        If VerkeerdeObject = True Then MsgBox "Element in deze laag is geen lijn of arc of polyline !", vbCritical
                
        Lengte = Lengte / 100
        Lengte = Format(Lengte, "0.0")
        
        Dim msg As String
        msg = "De gemeten lengte: " & Lengte & " m" & Chr(10) & Chr(13) & Chr(10) & Chr(13)
        msg = msg & "- reserve lengte: " & F_Main.TextBox1.Text & " m" & Chr(10) & Chr(13)
        msg = msg & "- rollengte: " & Lengte & " + " & F_Main.TextBox1.Text & " = " & F_Main.TextBox1.Text + Lengte & " m" & Chr(10) & Chr(13) & Chr(10) & Chr(13)
        
        MsgBox msg, vbInformation, "Lengte " & "[Laag: " & RetourObj.Layer & " / Kleur: " & RetourObj.Color & "]"
        
        
        '---------------------------------------------------------------------------------
        'JUIST INVULLEN MODEMACRO
        '---------------------------------------------------------------------------------
        
        Dim sModemacro As String
        Dim pos As Integer
        Dim sRechterdeel As String
        Dim sLinkerdeel As String
        
        sModemacro = ThisDrawing.GetVariable("modemacro")
        pos = InStr(1, sModemacro, "   ")
        
        If pos = 0 Then
                pos = InStr(1, sModemacro, "Rollengte=")
                If pos <> 0 Then
                    sModemacro = sModemacro & "   " & "Gemeten lengte= " & Lengte & " m."
                Else
                    sModemacro = "   " & "gemeten lengte= " & Lengte & " m."
                End If
        Else
                sModemacro = Left(sModemacro, pos) & "   " & "Gemeten lengte= " & Lengte & " m."
                sLinkerdeel = sLinkerdeel & "   "
        End If
                
        ThisDrawing.SetVariable "modemacro", sModemacro
   
        
        
        
End Sub

Attribute VB_Name = "M_6Fillet"
    
' totale fillet command d.m.v. sendcommand:  5 aug 2003  1,5 uur
' 6 aug 2003: 8:15 t/m
    
Sub Fillet5aug(FilletP1, FilletP2, Psnijpunt1, dFilletStraal)
'
'     Punt1 FilletP1, 1
'     Punt1 FilletP2, 2
'     Punt1 Psnijpunt1, 3

    ' ----------------------------------------------------------------------------
    ' Fillet d.m.v. sendcommand
    ' Door EBR 5 aug 2003
    ' ----------------------------------------------------------------------------
        

    Dim plineObj As AcadLWPolyline
    Dim Points(0 To 5) As Double
    
    Points(0) = FilletP1(0):      Points(1) = FilletP1(1)
    Points(2) = Psnijpunt1(0):     Points(3) = Psnijpunt1(1)
    Points(4) = FilletP2(0):      Points(5) = FilletP2(1)
    Set plineObj = ThisDrawing.ModelSpace.AddLightWeightPolyline(Points)
    plineObj.Update
    
    
    ThisDrawing.SendCommand ("FILLET" & vbCr & "R" & vbCr & dFilletStraal & vbCr & "P" & vbCr & "L" & vbCr)
    
    
    ' EXPLODEREN LAATST GETEKENDE POLYLINE EN LOSSE LINES VERWIJDEREN
    
    Dim explodedObjects As Variant
    Dim I As Integer
    Dim FilletArcObj As AcadEntity
    
    explodedObjects = plineObj.Explode
    
    For I = 0 To UBound(explodedObjects)
        'MsgBox explodedObjects(I).EntityName
        If explodedObjects(I).EntityName = "AcDbArc" Then Set FilletArcObj = explodedObjects(I)
        If explodedObjects(I).EntityName = "AcDbLine" Then explodedObjects(I).Delete
    Next
    
    plineObj.Delete
    
    If IsEmpty(FilletArcObj) Then
        MsgBox "Plaatsen bocht (fillet) bij aanvoerleiding met de eerste leiding is niet gelukt", vbInformation, "Let op"
        Exit Sub
    End If
        
    
    
    
End Sub

' ORIGINEEL PRINCIPE DOOR EBR:



'''Sub Fillet
'''
'''
'''    ' ----------------------------------------------------------------------------
'''    ' Fillet d.m.v. sendcommand
'''    ' Door EBR 5 aug 2003
'''    ' ----------------------------------------------------------------------------
'''
'''
'''    Dim LijnObj1 As AcadLine
'''    Dim LijnObj2 As AcadLine
'''    Dim Psnij As Variant
'''
'''    Set LijnObj1 = ThisDrawing.ModelSpace.Item(0)
'''    Set LijnObj2 = ThisDrawing.ModelSpace.Item(1)
'''
'''    Psnij = LijnObj1.IntersectWith(LijnObj2, acExtendBoth)
'''
'''    If IsEmpty(Psnij) Then MsgBox "Geen snijpunt gevonden", vbCritical: End
'''
'''    Dim Peind1 As Variant
'''    Dim Peind2 As Variant
'''
'''    Peind1 = LijnObj1.StartPoint
'''    Peind2 = LijnObj2.StartPoint
'''
'''
'''    Dim plineObj As AcadLWPolyline
'''    Dim points(0 To 5) As Double
'''    points(0) = Peind1(0):      points(1) = Peind1(1)
'''    points(2) = Psnij(0):       points(3) = Psnij(1)
'''    points(4) = Peind2(0):      points(5) = Peind2(1)
'''    Set plineObj = ThisDrawing.ModelSpace.AddLightWeightPolyline(points)
'''
'''
'''    Dim dStraal As Double
'''    dStraal = 5
'''    ThisDrawing.SendCommand ("FILLET" & vbCr & "R" & vbCr & dStraal & vbCr & "P" & vbCr & "L" & vbCr)
'''
'''End Sub

Attribute VB_Name = "M_6PlaatsenSlingers"
'gemaakt op 30 + 31 juli 2003

'30 juli 2003 C.A. 4 UUR
'31 JULI 2003 C.A. 4 UUR
'1+5 AUG2003 C.A. 2 UUR (ZIE OOK M_0Algemeen > function ZoekElementHandleRondPunt(P1, 0.1) !!

' ---------------------------------------------------------------------
' INSERT BLOCK MET SLINGER (ARC'S EN LINES)
' ---------------------------------------------------------------------


Sub OpvragenHOH()

    Dim dHOH As Double
    On Error Resume Next
    dHOH = F_Main.ComboBox2.Text
    If Err Then
        Err.Clear
        MsgBox "Opgegeven HOH-afstand is niet juist", vbCritical, "Let op"
        Exit Sub
    End If
    
    If dHOH = 0 Then MsgBox "Opgegeven HOH-afstand is niet juist", vbCritical, "Let op": Exit Sub
  
    Call PlaatsenSlingers(dHOH)
End Sub

Sub PlaatsenSlingers(dHOH)
    
    
    '--------------------------------------------------------------------
    'OPVRAGEN OSNAP-INSTELLING EN OSNAP INSTELLEN
    '--------------------------------------------------------------------
    
    Dim iOsnap As Integer
    iOsnap = ThisDrawing.GetVariable("OSMODE")
    
    'AANZETTEN OSNAP OP NEAREST + ENDPOINT
    ThisDrawing.ObjectSnapMode = True
    ThisDrawing.SetVariable "OSMODE", 513      ' NEAREST + ENDPOINT
    'ThisDrawing.SetVariable "OSMODE", 512        ' NEAREST toch fout 18 juni


    'TERUGSETTEN OSNAP
    'ThisDrawing.SetVariable "OSMODE", iOsnap
    '--------------------------------------------------------------------
    
    Dim p1 As Variant
    ' Dim GetentObj As AcadEntity
    Dim BlockRefObj As AcadBlockReference
    Dim sLaagNaam As String
    'Dim dHOH As Double 'aangeroepen vanuit subroutine
    Dim dRotatie As Double
    Dim sInspoint As String
    
    ' Me.Hide
    ' F_Main.Hide
    
    '--------------------------------------------------------------------
    'OPVRAGEN ELEMENT (IVM LAAGNAAM) ROND OPGEGEVEN PUNT
    '--------------------------------------------------------------------
    
    Dim sHandle As String
    Dim GevondenObj As AcadEntity
    
    ' ThisDrawing.Utility.GetEntity GetentObj, P1, "Selecteer beginpunt"        ' werkt niet mooi want geeft selectie-pickbox
    p1 = ThisDrawing.Utility.GetPoint(, "Selecteer beginpunt")
    sHandle = ZoekElementHandleRondPunt(p1, 0.1)
    
    If sHandle = "" Then
        MsgBox "Juiste laag kan niet worden bepaald.", vbInformation, "Geen element rond snappunt gevonden"
        sLaagNaam = ThisDrawing.ActiveLayer.Name
    Else
        Set GevondenObj = ThisDrawing.HandleToObject(sHandle)
        sLaagNaam = GevondenObj.Layer
    End If
            
     
    
            
    ' ------------------------------------
    ' sLaagNaam = GetentObj.Layer
    ' ThisDrawing.ActiveLayer.Name
    ' ------------------------------------
    
    
    'BEPALEN VAN DE KWADRANTEN
    Dim bXrichting As Boolean
    Dim bPositief As Boolean
    Dim bSpiegelen As Boolean
    
'''''    If Abs(P3(0) - P1(0)) > Abs(P3(1) - P1(1)) Then
'''''        bXrichting = True
'''''
'''''        If P3(0) - P1(0) > 0 Then
'''''            bPositief = True
'''''        Else
'''''            bPositief = False
'''''        End If
'''''    Else
'''''        bXrichting = False
'''''
'''''        If P3(1) - P1(1) > 0 Then
'''''            bPositief = True
'''''        Else
'''''            bPositief = False
'''''        End If
'''''    End If
    
'''''   MsgBox "bXrichting = " & bXrichting _
        & Chr(10) & Chr(13) & "bPositief = " & bPositief _
        & Chr(10) & Chr(13) & "dRotatie = " & dRotatie
   

    
    Dim p2 As Variant
    p2 = ThisDrawing.Utility.GetPoint(p1, "Selecteer eindpunt")
    
    'dHOH = 20
    dRotatie = ThisDrawing.Utility.AngleFromXAxis(p1, p2)
    
    '--------------------------------------------------------------------------------------
    'TERUGSETTEN OSNAP
    ThisDrawing.SetVariable "OSMODE", iOsnap
    '--------------------------------------------------------------------------------------
     
    'eerst inserten om te controleren of deze bestaat (wblock), IS NIET ECHT NODIG
    Dim Pins(0 To 2) As Double
    Pins(0) = 0
    Pins(1) = 0
    Pins(2) = 0
    InsertBlock "slinger-block", Pins, "0"
    Dim TestBlock As Object
    Set TestBlock = ThisDrawing.ModelSpace.Item(ThisDrawing.ModelSpace.Count - 1)
    If TestBlock.EntityName = "AcDbBlockReference" Then TestBlock.Delete Else MsgBox "Geen slinger-block gevonden": End
    
    'LET OP, OMDAT X, Y EN Z-SCALE NIET GELIJKS ZIJN ZULLEN DE ARC'S NA HET EXPLODEREN
    'VAN HET BLOCK VANZELF ELLIPSEN WORDEN.
    'DUS Z Y EN Z SCALE MOETEN GELIJK ZIJN. DOOR Z-SCALE GELIJK AAN DHOH TE MAKEN.
    'EVENTUEEL KAN OOK VERSCHALEN MET BlockRefObj.ScaleEntity P1, dHOH
    
    Set BlockRefObj = ThisDrawing.ModelSpace.InsertBlock(p1, "slinger-block", dHOH, dHOH, dHOH, dRotatie)
    
    BlockRefObj.Layer = sLaagNaam
    BlockRefObj.Update
    
    
        
    
    
     
    
    '--------------------------------------------------------------------------------------
    'MIRROR BLOCKREFERENCE (uitgezet)
    '--------------------------------------------------------------------------------------
    
    ZoomWindow p1, p2
    ' ZoomScaled 0.3, acZoomScaledRelative      voor 14 juni 2004 aanepast
    ZoomScaled 0.6, acZoomScaledRelative
    
'''    ' OUD VOOR 14 JUNI 2004
'''    Dim antw As String
'''    antw = MsgBox("leiding-slinger spiegelen ?", vbQuestion + vbYesNo, "Spiegelen")
'''    If antw = vbYes Then bSpiegelen = True
    
    
    ' IN COMMANDREGEL OPGEVEN JA OF NEE:
    Dim returnString As String
    returnString = ThisDrawing.Utility.GetString(True, "Spiegelen ?: Ja <Nee>")
    returnString = UCase(returnString)
    
    If returnString = "" Or UCase(Left(returnString, 1)) = "N" Then
        bSpiegelen = False
    Else
        bSpiegelen = True
    End If

    
    
    
    
    
    
    
'    If bSpiegelen = True Then
'        Dim MirrorObj As AcadBlockReference
'        Set MirrorObj = BlockRefObj.Mirror(P1, P2)
'        BlockRefObj.Delete
'        Set BlockRefObj = MirrorObj
'    End If
'
    ' VOLGENDE MANIER GEEFT EEN PREVIEW VAN BLOCKINSERTION:
    
    ' sInspoint = P1(0) & "," & P1(1) & "," & P1(2)
    ' ThisDrawing.SendCommand ("_-insert" & vbCr & "arcs" & vbCr & "Scale" & vbCr & dHoh & vbCr & sInspoint & vbCr)
    
'
'    If ThisDrawing.ModelSpace.Item(ThisDrawing.ModelSpace.Count - 1).EntityName <> "AcDbBlockReference" Then
'        MsgBox "Het laatst geplaatste element is geen blockreference", vbCritical
'        Exit Sub
'    Else
'        Set BlockRefObj = ThisDrawing.ModelSpace.Item(ThisDrawing.ModelSpace.Count - 1)
'    End If

    ' ---------------------------------------------------------------------
    ' EXPLODEREN BLOCK
    ' ---------------------------------------------------------------------


    Dim explodedObjects As Variant
    explodedObjects = BlockRefObj.Explode
    BlockRefObj.Delete
    
    Dim I As Integer
    For I = 0 To UBound(explodedObjects)
        'explodedObjects(I).Color = acRed
        explodedObjects(I).Layer = sLaagNaam
        explodedObjects(I).Update
        ' MsgBox explodedObjects(I).EntityName
    Next
    
    ' OBJECTEN IN DE BLOCKREFERENCE ZIJN GENUMMER VANAF HET GESELECTEERDE BEGINPUNT:
    
    ' BIJ INSERTEN VAN ARC EN EXPLODEREN WORDT EEN ARC EEN ELLIPSE (SCALE)
    Dim Obj1Arc As AcadArc
    Dim Obj2VertLijn As AcadLine
    Dim Obj3Arc As AcadArc
    Dim Obj4HorLijn As AcadLine
    Dim Obj5Arc As AcadArc
    Dim Obj6HorLijn As AcadLine
    Dim Obj7Arc As AcadArc
    Dim Obj8HorLijn As AcadLine
    Dim Obj9HorBeginLijn As AcadLine
    
        
    On Error Resume Next
        
    Set Obj1Arc = explodedObjects(0)
    Set Obj2VertLijn = explodedObjects(1)
    Set Obj3Arc = explodedObjects(2)
    Set Obj4HorLijn = explodedObjects(3)
    Set Obj5Arc = explodedObjects(4)
    Set Obj6HorLijn = explodedObjects(5)
    Set Obj7Arc = explodedObjects(6)
    Set Obj8HorLijn = explodedObjects(7)
    Set Obj9HorBeginLijn = explodedObjects(8)
    
    If Err Then
        Err.Clear
        MsgBox "Volgorde van entiteiten in block ARCS is niet juist.", vbCritical, "Let op"
        Exit Sub
    End If
        
    
    
    ' ---------------------------------------------------------------------
    ' STRETCHEN VAN DE LINES
    ' ---------------------------------------------------------------------
   
    Obj4HorLijn.Delete
    Obj6HorLijn.Delete
    
    'Obj8HorLijn.Color = acGreen
    Dim PeindObj8HorLijn As Variant
    PeindObj8HorLijn = Obj8HorLijn.EndPoint
    PeindObj8HorLijn(0) = p2(0)
    PeindObj8HorLijn(1) = p2(1)
    Obj8HorLijn.EndPoint = PeindObj8HorLijn
    
    
    
    Set Obj6HorLijn = Obj8HorLijn.Copy
    'Obj6HorLijn.Color = acBlue
    Obj6HorLijn.Move Obj6HorLijn.StartPoint, Obj7Arc.EndPoint
    
    
    
    Set Obj4HorLijn = Obj8HorLijn.Copy
    'Obj4HorLijn.Color = acYellow
    Obj4HorLijn.Move Obj4HorLijn.StartPoint, Obj3Arc.EndPoint
    '*** 6 aug: nu test op startpoint
    'Obj4HorLijn.Move Obj4HorLijn.StartPoint, Obj3Arc.StartPoint
    
    
    ' ---------------------------------------------------------------------
    ' VERPLAATSEN ARC
    ' ---------------------------------------------------------------------
    
    
    Obj5Arc.Move Obj5Arc.EndPoint, Obj6HorLijn.EndPoint
    '*** 6 aug: nu test op startpoint
    'Obj5Arc.Move Obj5Arc.EndPoint, Obj4HorLijn.EndPoint
    'Obj5Arc.Color = acRed
        
    
    
    'Obj4HorLijn.Color = acMagenta
    Obj4HorLijn.EndPoint = Obj5Arc.StartPoint
   
    
    'ThisDrawing.ActiveViewport.OrthoOn
    'ThisDrawing.ObjectSnapMode
    'ThisDrawing.ActiveViewport.OrthoOn
    
    '-------------------------------------------------------------------------
    'MIRROR DE AFZONDERLIJKE ELEMENTEN 6 AUG 2003
    '-------------------------------------------------------------------------
    
    If bSpiegelen = True Then
        Dim MirrorObj As AcadEntity
        Set MirrorObj = Obj1Arc.Mirror(p1, p2)
        Obj1Arc.Delete
        Set MirrorObj = Obj2VertLijn.Mirror(p1, p2)
        Obj2VertLijn.Delete
        Set MirrorObj = Obj3Arc.Mirror(p1, p2)
        Obj3Arc.Delete
        Set MirrorObj = Obj4HorLijn.Mirror(p1, p2)
        Obj4HorLijn.Delete
        Set MirrorObj = Obj5Arc.Mirror(p1, p2)
        Obj5Arc.Delete
        Set MirrorObj = Obj6HorLijn.Mirror(p1, p2)
        Obj6HorLijn.Delete
        Set MirrorObj = Obj7Arc.Mirror(p1, p2)
        Obj7Arc.Delete
        Set MirrorObj = Obj8HorLijn.Mirror(p1, p2)
        Obj8HorLijn.Delete
    End If
            
    
    '--------------------------------------------------------------------
    'EINDPUNT VAN GEVONDEN LIJN TRIMMEN (6 aug 2003)
    '--------------------------------------------------------------------
        
    'BEPALEN AAN WELKE KANT DE GESELECTEERDE LIJN GETRIMED MOET GAAN WORDEN
    
    
    If sHandle <> "" And GevondenObj.EntityName = "AcDbLine" Then
        If Lengte(p2, GevondenObj.StartPoint) > Lengte(p2, GevondenObj.EndPoint) Then
            GevondenObj.EndPoint = Obj9HorBeginLijn.EndPoint
        Else
            GevondenObj.StartPoint = Obj9HorBeginLijn.EndPoint
        End If
        
        Obj9HorBeginLijn.Erase
    Else
        MsgBox "Het geselecteerde element is geen lijn: element kan niet worden afgekort.", vbInformation, "Letop"
    End If
            
    
    
End Sub

Attribute VB_Name = "M_6TrimmenLijnen"


'---------------------------------------------------------------------------
' EBR OKTOBER 2002
' DIT PROGRAMMA TRIMT ALLE LIJNEN (AAN DE KORTSTE ZIJDE !), LANGS
' EEN OBJECT AF (LIJN, POLYLINE OF ARC)
' DE ARCS DIE AAN HET EIND OF BEGINPUNT VAN DE BETREFFENDE LIJN VERBONDEN
' (SELECTIESET) IS
' ZAL WORDEN VERPLAATST NAAR HET SNIJPUNT.
'----------------------------------------------------------------------------

Sub TrimmenLijnen()

    
   
    '-----------------------------------------------------------
    ' SELECTEER DE SNIJLIJN (LIJN OF POLYLINE)
    '-----------------------------------------------------------
    
    Dim returnObj As AcadObject
    Dim basePnt As Variant
    On Error Resume Next
    
    F_Main.Hide
        
 Dim iFoutSelectieTeller As Integer
    
              
Opnieuw1:

    If iFoutSelectieTeller > 1 Then Exit Sub 'End ***1 fewb 2004 was end
    
    ThisDrawing.Utility.GetEntity returnObj, basePnt, "Selecteer de (TRIM-) aanvoer- of retourleiding"
    
    If Err <> 0 Then
        Err.Clear
        If iFoutSelectieTeller < 1 Then MsgBox "Verkeerd geselecteerd", vbCritical, "Let op"
        iFoutSelectieTeller = iFoutSelectieTeller + 1
        GoTo Opnieuw1
    Else
        'Selectieset wordt niet goed gevuld als deze buiten beeld valt, daarom zoomextents
        
        ZoomExtents
        Call BepalenSnijpunt(returnObj)
        ZoomPrevious
    End If
    
    iFoutSelectieTeller = 0
    
    ThisDrawing.EndUndoMark
    '=einde
            
End Sub

Sub BepalenSnijpunt(LijnObj As Object)

'---------------------------------------------------------------------------------
' BEPAAL SNIJPUNTEN VAN ALLE LIJNEN MET DE GESELECTEERDE SNIJLIJN
' EN BEPAAL MET SUBROUTINE 'WegtrimmenBij' WAT DE KORTSTE ZIJDE IS
' HET EINDPUNT AAN DE KORTSTE ZIJDE ZAL WORDEN GEWIJZIGD
' EINDPUNT OF BEGINPUNT ZAL GELIJK WORDEN GEMAAKT MET HET BEREKENDE SNIJPUNT.
'---------------------------------------------------------------------------------

'lijnobj: is de geselecteerde snijpolyline (aanvoer, retour of gewoon een hulppolyline)

'plaats eerst undo-mark, omdat de lijnen anders per stuk moeten worden ge-undo't
ThisDrawing.StartUndoMark


Dim element As Object
Dim intPoints As Variant
Dim iAantalSnijpunten As Integer

Dim I As Integer, j As Integer, k As Integer
Dim str As String

Dim Xsnijp As Double
Dim Ysnijp As Double
Dim TrimZijde As String

Dim LijnenGevonden As Boolean
Dim SnijPuntengevonden As Boolean
Dim TrimZijdeBeginpunt As Boolean

Dim LaagNaam As String

LaagNaam = LijnObj.Layer


For Each element In ThisDrawing.ModelSpace
If element.EntityName = "AcDbLine" And element.Layer = LijnObj.Layer Then
If element.handle <> LijnObj.handle Then
    
        TrimZijdeBeginpunt = False
        intPoints = LijnObj.IntersectWith(element, acExtendNone)
        
        
        
        If VarType(intPoints) <> vbEmpty Then
            SnijPuntengevonden = True
            
            'INDIEN MEER DAN 2 SNIJPUNTEN DAN TEKENING COTNROLEREN
            
            iAantalSnijpunten = (UBound(intPoints) + 1) / 3
            'MsgBox iAantalSnijpunten
            
            If iAantalSnijpunten > 1 Then
                MsgBox "element " & element.handle & " heeft " & iAantalSnijpunten & " snijpunten met de opschuif-polyline. " _
                & Chr(10) & Chr(13) & "Opschuiven onmogelijk: controleer de tekening", vbCritical, "Controleer tekening."
                Call ZoomInOpElement(element, True)
                End
            End If
            
            For I = LBound(intPoints) To UBound(intPoints)
                'ListBox1.AddItem ELEMENT.Handle & "  " & intPoints(j) & "," & intPoints(j + 1) & "," & intPoints(j + 2)
                              
                Xsnijp = intPoints(j)
                Ysnijp = intPoints(j + 1)
                
                
                    LijnenGevonden = True
                    TrimZijde = BepalenTrimZijde(element, Xsnijp, Ysnijp)
                    
                    If TrimZijde = "beginpunt" Then
                        TrimZijdeBeginpunt = True
                        Call VerplaatsenArcs(element.StartPoint, intPoints, TrimZijdeBeginpunt, LaagNaam)
                        element.StartPoint = intPoints
                        
                    Else
                        TrimZijdeBeginpunt = True = False
                        Call VerplaatsenArcs(element.EndPoint, intPoints, TrimZijdeBeginpunt, LaagNaam)
                        element.EndPoint = intPoints
                    End If
                    
                    'VERPLAATSEN ARCS
                    
               
                
                Exit For
                'I = I + 2
                'j = j + 3
                'k = k + 1
            Next
        End If
      
End If
End If
Next element

If LijnenGevonden = False Then MsgBox "Geen leidingen (lines) in dezelfde laag als de geselecteerde (aanvoer) polyline gevonden.", vbExclamation, "Leidingleg-programma"
If SnijPuntengevonden = False Then MsgBox "Geen leidingen worden gesneden door de geselecteerde (aanvoer) polyline.", vbExclamation, "Leidingleg-programma"
       
       
 
End Sub


Function BepalenTrimZijde(LijnObj As Object, Xsnijp As Double, Ysnijp) As String

    '-------------------------------------------------------
    'BEPALEN LENGTE VANAF HET SNIJPUNT NAAR ZOWEL HET BGIN-
    'ALS HET EINDPUNT VAN DE LIJN
    '-------------------------------------------------------

    Dim Pbegin As Variant
    Dim Peind As Variant
    
    Pbegin = LijnObj.StartPoint
    Peind = LijnObj.EndPoint
    
    'BEREKENEN LENGTE VAN SNIJPUNT TOT BEGINPUNT LIJN
    Dim Lengte1 As Double
    Lengte1 = Sqr((Pbegin(0) - Xsnijp) ^ 2 + (Pbegin(1) - Ysnijp) ^ 2)
    
    'BEREKENEN LENGTE VAN SNIJPUNT TOT EINDPUNT LIJN
    Dim Lengte2 As Double
    Lengte2 = Sqr((Peind(0) - Xsnijp) ^ 2 + (Peind(1) - Ysnijp) ^ 2)
    
    
    If Abs(Lengte2) > Abs(Lengte1) Then
        'MsgBox "WEGTRIMMEN BIJ BEGINPUNT" & LijnObj.Handle
        BepalenTrimZijde = "beginpunt"
    Else
        'MsgBox "WEGTRIMMEN BIJ EINDPUNT " & LijnObj.Handle
        BepalenTrimZijde = "eindpunt"
    End If
    
    'Update
    
End Function

Sub VerplaatsenArcs(OorspronkelijkeEindpuntLijn, NieuweEindpuntLijn, TrimZijdeBeginpunt, LaagNaam)

    'M.B.V. EEN SELECTIE-WINDOW OM HET GEVONDEN EINDPUNT (OF BEGINPUNT) VAN DE
    'LIJN DE BIJBEHORENDE ARC SELECTEREN. DEZE VERVOLGENS VERPLAATSEN.

    'If TrimZijdeBeginpunt = True Then MsgBox "1e lijn aan beginpunt-zijde inkorten"
    'If TrimZijdeBeginpunt = False Then MsgBox "1e lijn aan eindpunt-zijde inkorten"
     
    '----------------------------------------------------------------------
    'VOORGAANDE SELECTIESETS VERWIJDEREN
    '----------------------------------------------------------------------
    
    Dim ssetObj As AcadSelectionSet
    For Each ssetObj In ThisDrawing.SelectionSets
        ssetObj.Clear
        ssetObj.Delete
    Next ssetObj
    
    
    '----------------------------------------------------------------------
    'GROOTTE VAN SELECTIE-WINDOW INSTELLEN:
    '----------------------------------------------------------------------
    
    Dim P1sset(0 To 2) As Double
    Dim P2sset(0 To 2) As Double
    
    P1sset(0) = OorspronkelijkeEindpuntLijn(0) - 1
    P1sset(1) = OorspronkelijkeEindpuntLijn(1) - 1
    
    P2sset(0) = OorspronkelijkeEindpuntLijn(0) + 1
    P2sset(1) = OorspronkelijkeEindpuntLijn(1) + 1
    
    '----------------------------------------------------------------------
    'AANMAKEN SELECTIESET OM EINDPUNT/ BEGINPUNT VAN LIJN:
    '----------------------------------------------------------------------
    
    ReDim gpCode(0) As Integer
    gpCode(0) = 0
    ReDim dataValue(0) As Variant
    dataValue(0) = "Arc"
    
    Dim groupCode As Variant, dataCode As Variant
    groupCode = gpCode
    dataCode = dataValue
    
     
    
    Set ssetObj = ThisDrawing.SelectionSets.Add("TEST_SSET")
    'ssetObj.SelectOnScreen
    ssetObj.Select acSelectionSetCrossing, P1sset, P2sset, groupCode, dataCode
    
    'UITFILTEREN ARC:
    
    Dim element As Object
    Dim ArcObj As AcadArc
    Dim ArcGevonden As Boolean
    
    For Each element In ssetObj
        If element.EntityName = "AcDbArc" Then
            Set ArcObj = element
            ArcGevonden = True
            Exit For
        End If
    Next element
    
    ssetObj.Clear
    ssetObj.Delete
    
    '----------------------------------------------------------------------
    'AANMAKEN SELECTIESET OM EINDPUNT/ BEGINPUNT VAN LIJN:
    '----------------------------------------------------------------------
   
    
    Dim PuntObj As AcadPoint
    Dim Pss As Variant      'punt selectieset
    Dim StartpointArcGevonden As Boolean
    
    If ArcGevonden = True Then

            'Bepalen of start o endpoint van de arc gevonden is.
            If Lengte(ArcObj.StartPoint, OorspronkelijkeEindpuntLijn) > Lengte(ArcObj.EndPoint, OorspronkelijkeEindpuntLijn) Then
                'MsgBox "Endpunt van Arc gevonden"
                StartpointArcGevonden = True
                'Set Puntobj = ThisDrawing.ModelSpace.AddPoint(ArcObj.StartPoint)
                Pss = ArcObj.StartPoint
            Else
                'MsgBox "Startpoint van Arc gevonden"
                StartpointArcGevonden = False
                'Set Puntobj = ThisDrawing.ModelSpace.AddPoint(ArcObj.EndPoint)
                Pss = ArcObj.EndPoint
            End If
            
            
            'SELECTIE MAKEN OM START- OF ENDPOINT VAN ARC
            '*** 26 MAART 2003 WAS 4, GEWIJZIGD IN 1:
            P1sset(0) = Pss(0) - 1
            P1sset(1) = Pss(1) - 1
            
            P2sset(0) = Pss(0) + 1
            P2sset(1) = Pss(1) + 1
            
            '----------------------------------------------------------------------
            'AANMAKEN SELECTIESET OM EINDPUNT/ BEGINPUNT VAN GEVONDEN ARC:
            '----------------------------------------------------------------------
            
            ReDim gpCode(0) As Integer
            gpCode(0) = 0
            ReDim dataValue(0) As Variant
            dataValue(0) = "Line"
            
            'Dim groupCode As Variant, dataCode As Variant
            groupCode = gpCode
            dataCode = dataValue
            
            Set ssetObj = ThisDrawing.SelectionSets.Add("TEST_SSET")
            'ssetObj.SelectOnScreen
            ssetObj.Select acSelectionSetCrossing, P1sset, P2sset, groupCode, dataCode
            
            Dim LijnObj2 As AcadLine
            Dim LijnObj2Gevonden As Boolean
            
            For Each element In ssetObj
                If element.EntityName = "AcDbLine" Then
                    '*** nieuw 26 maart 2003: if conditie toegevoegd omdat verkeerde elementen werden gevonden
                    'daarom ook laagnaam als argument in de subroutine toegevoegd.
                    
                    If element.Layer = LaagNaam Then
                        Set LijnObj2 = element
                        LijnObj2Gevonden = True
                        Exit For
                    End If
                End If
            Next element
            
            ssetObj.Clear
            ssetObj.Delete
            
            ArcObj.Move OorspronkelijkeEindpuntLijn, NieuweEindpuntLijn
            
            If LijnObj2Gevonden = True Then
                'MsgBox LijnObj2.handle
                
                If Lengte(LijnObj2.StartPoint, Pss) > Lengte(LijnObj2.EndPoint, Pss) Then
'                    MsgBox "Eindpunt van lijn 2 gevonden"
'
                    If StartpointArcGevonden = True Then
                        LijnObj2.EndPoint = ArcObj.StartPoint
                    Else
                        LijnObj2.EndPoint = ArcObj.EndPoint
                    End If

                    'LijnObj2.Color = acMagenta
                
                Else
                    'MsgBox "Startpunt van lijn 2 gevonden"

                    If StartpointArcGevonden = True Then
                        LijnObj2.StartPoint = ArcObj.StartPoint
                    Else
                        LijnObj2.StartPoint = ArcObj.EndPoint
                    End If

                    'LijnObj2.Color = acMagenta
                
                End If
                
                
                
            End If
                       
                      
            
            'UPDATEN IS ZEER BELANGRIJK, ANDERS FOUTEN !
            ArcObj.Update
    End If
    'End 'test eenmalige lijnverschuiving
    
End Sub


Sub Undomark()
    'UNDO HET TRIMMEN EN VERPLAATEN VAN DE ARCS TOT DE UNDO-MARK
    ThisDrawing.Regen True
    Application.RunMacro "Undomark1"
End Sub

Sub Undomark1()
    ThisDrawing.SendCommand "UNDO" & vbCr & "B" & vbCr
    Application.Update
End Sub

Attribute VB_Name = "M_7WijzigenLengte"
    Option Explicit
    
    Sub WijzigenLengte()
    ' --------------------------------------------------------------
    ' ACHTERAF HANDMATIG WIJZIGEN VAN LEIDINGLENGTE (2 LIJNEN + ARC)
    ' EBR: 29 APRIL 2004
    ' --------------------------------------------------------------
    
    On Error Resume Next
    
    Dim dReserveLengte As Double
    dReserveLengte = F_Main.TextBox1.Text
    
    ' --------------------------------------------------------------
    ' SELECTEREN LIJN
    ' --------------------------------------------------------------
    
    F_Main.Hide

    Dim LijnObj1 As AcadLine
    Dim bEindpuntInkortenLijn1 As Boolean
    Dim bEindpuntInkortenLijn2 As Boolean
    
    Dim P0 As Variant
    Dim p1 As Variant
    Dim p2 As Variant
    Dim P3 As Variant
    Dim P6 As Variant

    On Error Resume Next

    ThisDrawing.Utility.GetEntity LijnObj1, p1, "Selecteer leiding:"
    If Err <> 0 Then
        Err.Clear
        'MsgBox "Verkeerd geselecteerd"
        Exit Sub
    End If

    If LijnObj1.EntityName <> "AcDbLine" Then
        MsgBox "Geen lijn geselecteerd.", vbCritical, "Let op"
        Exit Sub
    End If
        

    ' --------------------------------------------------------------
    ' BEPALEN OF BEGIN OF EINDPUNT GESELECTEERD IS
    ' --------------------------------------------------------------

    If Lengte(LijnObj1.EndPoint, p1) > Lengte(LijnObj1.StartPoint, p1) Then
        'MsgBox "lijn bij beginpunt geselecteerd"
        p2 = LijnObj1.StartPoint
        P0 = LijnObj1.EndPoint
        bEindpuntInkortenLijn1 = False
    Else
        'MsgBox "lijn bij eindpunt geselecteerd"
        p2 = LijnObj1.EndPoint
        P0 = LijnObj1.StartPoint
        bEindpuntInkortenLijn1 = True
    End If
    
    
    ' --------------------------------------------------------------
    ' ZOEK ARC OP EINDPUNT VAN LIJN
    ' ZOEK VOLGENDE LIJN AAN ANDERE ZIJDE VAN GEVONDEN ARC
    ' --------------------------------------------------------------
    
    
    Dim sZoekHandle As String
    Dim ArcObj As AcadObject
    
    sZoekHandle = ZoekElementHandleRondPunt(p2, 3, LijnObj1.handle)
    Set ArcObj = ThisDrawing.HandleToObject(sZoekHandle)
    
    If ArcObj.EntityName <> "AcDbArc" Then
        MsgBox "Geen bocht (arc) gevonden.", vbInformation, "Inkorten niet mogelijk"
        Exit Sub
    End If
    
    
    'BEPAAL OF BEGIN- OF EINDPUNT VAN ARC GEVONDEN IS:
    
    Dim bBeginpuntGevondenArc As Boolean
    bBeginpuntGevondenArc = BepaalBeginpunt(p2, ArcObj)
    
    If bBeginpuntGevondenArc = True Then
        P3 = ArcObj.EndPoint
    Else
        P3 = ArcObj.StartPoint
    End If
    
    'Punt (P3)
    
    
    'ZOEK LIJN AAN ANDERE ZIJDE VAN ARC:
    
    Dim LijnObj2 As AcadLine
    sZoekHandle = ZoekElementHandleRondPunt(P3, 3, ArcObj.handle)
    
    Set LijnObj2 = ThisDrawing.HandleToObject(sZoekHandle)
    
    
    'BEPAAL OF BEGIN- OF EINDPUNT VAN LINE GEVONDEN IS:
    
    Dim sBeginpuntGevondenLijn2 As Boolean
    sBeginpuntGevondenLijn2 = BepaalBeginpunt(P3, LijnObj2)
    
    If sBeginpuntGevondenLijn2 = True Then
        bEindpuntInkortenLijn2 = False
    Else
        bEindpuntInkortenLijn2 = True
    End If
        
    
    
    ' --------------------------------------------------------------
    ' OPVRAGEN MODEMACRO
    ' --------------------------------------------------------------
         
''''    Dim sModemacro As String
''''    Dim pos As Integer
''''    Dim sTekst As String
''''
''''    Dim sGemetenLengte As String
''''    Dim sRollengte As String
''''
''''    ' sModemacro = "Gemeten lengte=5 m."
''''    sModemacro = ThisDrawing.GetVariable("modemacro")
''''
''''    pos = InStr(1, sModemacro, "Gemeten lengte=")
''''    If pos <> 0 Then
''''        sTekst = Right(sModemacro, Len(sModemacro) - 15)
''''        pos = InStr(1, sTekst, "=")
''''        sTekst = Right(sTekst, Len(sTekst) - pos)
''''        pos = InStr(1, sTekst, " m.")
''''        sTekst = Left(sTekst, pos)
''''        sTekst = Trim(sTekst)
''''        sGemetenLengte = sTekst
''''        ' MsgBox "Gemeten lengte=" & sTekst
''''    End If
''''
''''    pos = InStr(1, sModemacro, "Rollengte=")
''''    If pos <> 0 Then
''''        sTekst = Right(sModemacro, Len(sModemacro) - 10)
''''        pos = InStr(1, sTekst, "m")
''''        sTekst = Left(sTekst, pos - 1)
''''        sTekst = Trim(sTekst)
''''        sRollengte = sTekst
''''        ' MsgBox " Rollengte=" & sTekst
''''    End If
''''
''''    Dim dRollengte As Double
''''    Dim dGemetenLengte As Double
''''
''''    'dGemetenLengte = CDbl(sGemetenLengte)
''''    'dRollengte = CDbl(sRollengte)
''''
''''    sGemetenLengte = Replace(sGemetenLengte, ",", ".")
''''
''''    dGemetenLengte = Val(sGemetenLengte)
''''    If Err Then MsgBox Err.Description
''''    dRollengte = Val(sRollengte)
''''    If Err Then MsgBox Err.Description

    
    ' *************************************************************
    ' BOVENSTAANDE 14 JUNI 2004 VERVANGEN
    ' GEGEVENS NIET LEZEN UIT MODEMACRO, MAAR UIT REGISTRY
    ' *************************************************************
    
    Dim dRollengte As Double
    Dim dGemetenLengte As Double
    
    dGemetenLengte = F_LengteMonitor.TextBox1.Text
    
    dRollengte = GetSetting("Leidinglegprogramma", "Startup", "InvoerRolLengte", "")
    If Err Then
        Err.Clear
        dRollengte = 0
    End If
    
    ' --------------------------------------------------------------
    ' OPGEVEN LENGTEVERSCHIL
    ' --------------------------------------------------------------
   
         
    Dim dLengteVerschil As Double
    dLengteVerschil = InputBox("Geef lengteverschil in cm op (+ of -)" _
        & Chr(10) & Chr(13) _
        & Chr(10) & Chr(13) & "*  gemeten lengte=" & dGemetenLengte & " m" _
        & Chr(10) & Chr(13) & "-  Laatst opgegeven rollengte=" & dRollengte & " m" _
        & Chr(10) & Chr(13) & "-  reserve lengte=" & dReserveLengte & " m" _
        & Chr(10) & Chr(13) _
        & Chr(10) & Chr(13) & "-  lengteverschil=" & Round((dRollengte - dGemetenLengte - dReserveLengte), 1) & " m" _
        & Chr(10) & Chr(13) _
        & Chr(10) & Chr(13) _
        & "                           [Enter] = bevestigen" _
        , "Wijzigen leidinglengte", Round(100 * (dRollengte - dGemetenLengte - dReserveLengte), 1))
        
    dLengteVerschil = dLengteVerschil / 2
    
    If Err Then
        Err.Clear
        dLengteVerschil = 0
    End If
    
    If dLengteVerschil = 0 Then
        
        P6 = ThisDrawing.Utility.GetPoint(ArcObj.Center, "Geef eindpunt aan")
        
        dLengteVerschil = Lengte(ArcObj.Center, P6)
    
        If Lengte(P0, p1) < Lengte(P0, P6) Then
            'MsgBox "verlengen"
        Else
            'MsgBox "inkorten"
            dLengteVerschil = -dLengteVerschil
        End If
        
        
        
        If Err Then
            Err.Clear
            'Exit Sub
        End If
        
    End If
    
    
    
    ' --------------------------------------------------------------
    ' INKORTEN LIJNEN
    ' --------------------------------------------------------------
      
    LijnlengteWijzigen LijnObj1, LijnObj1.Length + dLengteVerschil, bEindpuntInkortenLijn1
    
    LijnlengteWijzigen LijnObj2, LijnObj2.Length + dLengteVerschil, bEindpuntInkortenLijn2
      
    
    ' --------------------------------------------------------------
    '  VERPLAATSEN ARC
    ' --------------------------------------------------------------
    
    'BEPALEN OF BEGIN- OF EINDPUNT VAN LIJN GEVONDEN IS
    
    Dim P5 As Variant
    If bEindpuntInkortenLijn1 = True Then
        P5 = LijnObj1.EndPoint
    Else
        P5 = LijnObj1.StartPoint
    End If
    
    
    If bBeginpuntGevondenArc = True Then
        ArcObj.Move ArcObj.StartPoint, P5
    Else
        ArcObj.Move ArcObj.EndPoint, P5
    End If
    
    ArcObj.Update

      

    
End Sub




    
    
''''    Dim sHoekInGraden As String         'LET OP STRING
''''    sHoekInGraden = ThisDrawing.Utility.AngleToString(ReturnObj1.Angle, acDegrees, 3)
''''
''''    'ThisDrawing.SetVariable "SNAPANG", sHoekInGraden           'WERKT GOED: ALS STRING MAAR NIET IN GROTER PROGRAMMADEEL ?
''''    ThisDrawing.ActiveViewport.SnapRotationAngle = ReturnObj1.Angle
''''
''''
''''
''''    'ThisDrawing.SetVariable "ORTHO", "ON"                      'GEEFT ERROR
''''    ThisDrawing.ActiveViewport.OrthoOn = True                  'LUKT OOK NIET
''''    'ThisDrawing.SendCommand ("ORTHO" & vbCr & "ON" & vbCr)      'GAAT WEL



   
     
''''   ThisDrawing.Regen acActiveViewport
''''
''''    Dim currViewport As AcadViewport
''''    Set currViewport = ThisDrawing.ActiveViewport
''''    ThisDrawing.ActiveViewport = currViewport
''''    Application.Update
''''
''''
''''    'ThisDrawing.ActiveViewport = ThisDrawing.ActiveViewport
''''    'ThisDrawing.ActiveSpace = acModelSpace
''''    'ThisDrawing.Regen True
''''
''''    P3 = ThisDrawing.Utility.GetPoint(P2, "Geef de richting aan.")
'''''
'''''    ThisDrawing.ActiveViewport.OrthoOn = False
'''''    ThisDrawing.ActiveViewport.SnapRotationAngle = 0
''''

Function BepaalBeginpunt(Punt, Obj) As Boolean
    'EBR 29 APRIL 2004
    'DEZE FUNCTIE BEPAALT OF BEGIN- OF EINDPUNT VAN LINE OF ARC GEVONDEN IS.

    Select Case Obj.EntityName
    Case "AcDbLine", "AcDbArc"
    Case Else
        MsgBox "Geen line of Arc aangegeven", vbExclamation, "Let op"
        End
    End Select
    
    
    If Lengte(Punt, Obj.EndPoint) > Lengte(Punt, Obj.StartPoint) Then
        'MsgBox "beginpunt gevonden"
        BepaalBeginpunt = True
    Else
        'MsgBox "eindpunt gevonden"
        BepaalBeginpunt = False
    End If
End Function

Attribute VB_Name = "M_BepaalLineAanPolyline"
Public Function BepaalLijnAanEindePolyline(ObjPolyline As Object) As String

    ZoomExtents         'LET OP, ZOOM EXTENTS GEHEEL BOVEN SELECTIESET PLAATSEN, ANDERS LEGE SELECTIESET !!
    
    '2 okt 2002
    '-----------------------------------------------------------------------------------
    'DEZE FUNCTIE BEPAALT WELKE LIJN ZICH BEVINDT AAN HET AANPUNT VAN EEN LWT-POLYLINE
    'INPUT: OBJECT LWT-POLYLINE
    'OUTPUT: HANDLE VAN DE LINE
    '-----------------------------------------------------------------------------------
    
    'MsgBox ObjPolyline.handle
    'Dim objPline As Object
    'Set objPline = ThisDrawing.ModelSpace.Item(ThisDrawing.ModelSpace.Count - 1)
    
    Dim intVCnt As Integer
    Dim varCords As Variant
    Dim varVert As Variant
    
    coord = ObjPolyline.Coordinates
     
    'MsgBox "Eerste x =" & coord(0)
    'MsgBox "Eerste Y =" & coord(1)
    
    'bepalen of tellen van het aantal vertexten
    For Each varVert In coord
      intVCnt = intVCnt + 1
    Next
     
    'MsgBox "Laatste x =" & coord(intVCnt - 2)
    'MsgBox "Laatste y =" & coord(intVCnt - 1)
    
    '----------------------------------------------------------
    ' Create the selection set
    '----------------------------------------------------------
    
    Dim ssetObj As AcadSelectionSet
    For Each ssetObj In ThisDrawing.SelectionSets
        'ssetObj.Clear
        ssetObj.Delete
    Next ssetObj
    
    Set ssetObj = ThisDrawing.SelectionSets.Add("SSET")

    Dim mode As Integer
    Dim corner1(0 To 2) As Double
    Dim corner2(0 To 2) As Double

    mode = acSelectionSetCrossing
    corner1(0) = coord(intVCnt - 2) - 2
    corner1(1) = coord(intVCnt - 1) - 2
    corner1(2) = 0

    corner2(0) = coord(intVCnt - 2) + 2
    corner2(1) = coord(intVCnt - 1) + 2
    corner2(2) = 0

    ssetObj.Select mode, corner1, corner2
 
    
    
    Dim element As Object
    Dim tl As Integer
    Dim LijnObj As Object
    
    '*** MsgBox "HIER FATEL ERROR ?", vbExclamation
    
    
    
    For Each element In ssetObj
        If element.handle <> ObjPolyline.handle Then
            If element.EntityName = "AcDbLine" Then
                tl = tl + 1
                Set LijnObj = element
            End If
        End If
    Next element
        
    ssetObj.Clear
    ssetObj.Delete
    
    If tl = 0 Then SchrijfLogFile ("Geen leiding (lijn) verbonden met het eindpunt van de aanvoer leiding (polyline) (of UCS-niet in World ?) OF eerst zoom-extents")
    If tl > 1 Then SchrijfLogFile ("Meerdere leidingen (lijnen) verbonden met het eindpunt van de aanvoer leiding (polyline)")
    
    If tl = 0 Then MsgBox "Geen leiding (lijn) verbonden met het eindpunt van de aanvoer leiding (polyline) (UCS niet in World ?) OF eerst zoom-extents", vbCritical: End
    If tl > 1 Then MsgBox "Meerdere leidingen (lijnen) verbonden met het eindpunt van de aanvoer leiding (polyline)", vbCritical: End
   

    SchrijfLogFile ("Gevonden lijn aan einde polyline: handle=" & LijnObj.handle)
    'MsgBox "gevonden lijn: " & LijnObj.handle
    BepaalLijnAanEindePolyline = LijnObj.handle
    
    ZoomPrevious
    
End Function

Attribute VB_Name = "M_BerekenLengtePolyline"
Public BerekendeAfstTotVertex As Double

'VOORBEELD AANROEP VANUIT FORM:
'Private Sub CommandButton8_Click()
'    Dim objPline As Object
'    Dim LengtePolyline As Double'
'    Set objPline = ThisDrawing.ModelSpace.Item(ThisDrawing.ModelSpace.Count - 1)
'
'    Dim PSnij(0 To 2) As Double
'    PSnij(0) = 50
'    PSnij(1) = 50
'    PSnij(2) = 0
'
'    LengtePolyline = M_BerekenLengtePolyline.LengtePolyline(objPline, PSnij, False)
'    MsgBox "LengtePolyline=" & LengtePolyline'
'End Sub



Public Function LengtePolyline(objPline As Object, Psnij As Variant, bZoekLengte As Boolean) As Double
   
    'Dim DebugMode As Boolean
    'DebugMode = True
    
    Dim AfstSnijpTotVertex As Double
    Dim KortsteLengte As Double
    KortsteLengte = 100000
    
    
    '-------------------------------------------------------------------------------------
    'DIT PROGRAMMA
    '   - BEREKEND DE LENGTE VAN EEN LWT-POLYLINE
    '   - BEPAALD DE KORTSTE AFSTAND VAN DE POLYLINEVERTEX MET EEN OPGEGEVEN SNIJPUNT
    '-------------------------------------------------------------------------------------
    
    F_Main.ListBox3.Clear   'opslaan coordinaten van lwt-polyline
    
    
    If objPline.EntityName <> "AcDbPolyline" Then
        MsgBox "Het geslecteerde element is geen LWT-Polyline", vbCritical, "Let op"
        Exit Function
    End If
       
    Dim VoorgaandeLengte As Double
    '------------------------------------------------------
    'BEREKENEN LENGTE
    '------------------------------------------------------
    
    Dim intVCnt As Integer
    Dim varCords As Variant
    Dim varVert As Variant
    Dim varCord As Variant
    Dim varNext As Variant
    Dim intCrdCnt As Integer
    Dim dblTemp As Double
    Dim dblArc As Double
    Dim dblAng As Double
    Dim dblChord As Double
    Dim dblInclAng As Double
    Dim dblRad As Double
    
      
    varCords = objPline.Coordinates
    
    For Each varVert In varCords
      intVCnt = intVCnt + 1
    Next
    
    For intCrdCnt = 0 To intVCnt / 2 - 1              'For LWPoly 2 - 1 else 3 -1
           
      
      If intCrdCnt < intVCnt / 2 - 1 Then
        If objPline.GetBulge(intCrdCnt) = 0 Then
          varCord = objPline.Coordinate(intCrdCnt)
          varNext = objPline.Coordinate(intCrdCnt + 1)
          
          VoorgaandeLengte = dblTemp
          'computes a simple Pythagorean length
          dblTemp = dblTemp + Sqr(((varCord(0) - varNext(0)) ^ 2) + ((varCord(1) - varNext(1)) ^ 2))
                            
            'AFBEELDEN COORDINATEN VAN LWT-POLYLINE
            F_Main.ListBox3.AddItem AFR(varCord(0)) & " EN " & AFR(varCord(1))
                       
                    
        Else
          'If there is a bulge we need to get an arc length
          varCord = objPline.Coordinate(intCrdCnt)
          varNext = objPline.Coordinate(intCrdCnt + 1)
          dblChord = Sqr(((varCord(0) - varNext(0)) ^ 2) + ((varCord(1) - varNext(1)) ^ 2))
          
          'Bulge is the tangent of 1/4 of the included angle between
          'vertices. So we reverse the process to get the included angle
          dblInclAng = Atn(Abs(objPline.GetBulge(intCrdCnt))) * 4
          dblAng = (dblInclAng / 2) - ((Atn(1) * 4) / 2)
          dblRad = (dblChord / 2) / (Cos(dblAng))
          dblArc = dblInclAng * dblRad
          dblTemp = dblTemp + dblArc
        End If
      End If
      
        ' -------------------------------------------------------------------------
        ' BEREKENEN KORTSTE AFSTAND TOT SNIJPUNT
        ' -------------------------------------------------------------------------
        AfstSnijpTotVertex = Sqr(((varCord(0) - Psnij(0)) ^ 2) + ((varCord(1) - Psnij(1)) ^ 2))
        If AfstSnijpTotVertex < KortsteLengte Then KortsteLengte = AfstSnijpTotVertex
        
        If intCrdCnt Mod 2 = 0 Then
            'ALLEEN ALS HET BEGINPUNT IS
            If Debugmode = True Then MsgBox "Afstand van het opgegeven snijpunt tot de 'aktieve' vertex =" & AfstSnijpTotVertex
        End If
        
        If bZoekLengte = True Then
            If AfstSnijpTotVertex = BerekendeAfstTotVertex Then
            
                If Debugmode = True Then MsgBox "LENGTE POLYLINE VAN BEGINPUNT (POLYLINE) TOT HET OPGEGEVEN SNIJPUNT = " & AfstSnijpTotVertex + VoorgaandeLengte, vbInformation
                        
                'LengtePolyline = dblTemp                                       'LENGTE VAN SNIJPUNT TOT DICHTSTBIJZIJNDE VERTEX
                  
                        
                ' BEPALEN OF DE VERTEX EEN 'BEGIN- OF EINDPUNT' IS
                If intCrdCnt Mod 2 = 0 Then
                    'MsgBox "Snijpunt bij Beginpunt"
                    'SNIJPUNT BOVEN HET MIDDEN (AAN KANT VAN BEGINPUNT)
                    LengtePolyline = VoorgaandeLengte + AfstSnijpTotVertex
                Else
                    'MsgBox "Snijpunt bij eindpunt"
                    'SNIJPUNT ONDER HET MIDDEN (AAN KANT VAN BEGINPUNT)
                    LengtePolyline = VoorgaandeLengte - AfstSnijpTotVertex
                End If
                        
                 
                Exit Function
            End If
        End If
    
    Next
    
        'AFBEELDEN LAATSTE COORDINAATVAN LWT-POLYLINE
        F_Main.ListBox3.AddItem AFR(varNext(0)) & " EN " & AFR(varNext(1))
        
        If Debugmode = True Then MsgBox "KortsteLengte=" & KortsteLengte
        BerekendeAfstTotVertex = KortsteLengte  'DEZE OPSLAAN ALS PUBLIC, OM HER TE GEBRUIKEN !! NA EERSTE BEREKENING VOOR DE TWEEDE KAAR HIER NAARTOE REKENEN.
        
    VoorgaandeLengte = dblTemp
    LengtePolyline = dblTemp
    
  
End Function

Attribute VB_Name = "M_BerekenLengtePolyline2"
Public Function LengtePolyline2(objPline As Object) As Double
 
    
    'MsgBox objPline.handle
    '-------------------------------------------------------------------------------------
    'DIT PROGRAMMA
    '   - BEREKEND DE LENGTE VAN EEN LWT-POLYLINE
    '-------------------------------------------------------------------------------------
            
    
    If objPline.EntityName <> "AcDbPolyline" Then
        MsgBox "Het geslecteerde element is geen LWT-Polyline", vbCritical, "Let op"
        Exit Function
    End If
       
    
    '------------------------------------------------------
    'BEREKENEN LENGTE
    '------------------------------------------------------
    
    Dim intVCnt As Integer  'interval counter
    Dim varCords As Variant
    Dim varVert As Variant  'vertexen
    Dim varCord As Variant
    Dim varNext As Variant
    Dim intCrdCnt As Integer
    Dim dblTemp As Double
    Dim dblArc As Double
    Dim dblAng As Double
    Dim dblChord As Double
    Dim dblInclAng As Double
    Dim dblRad As Double
    
      
    varCords = objPline.Coordinates
    
    For Each varVert In varCords
      intVCnt = intVCnt + 1
    Next
    
    For intCrdCnt = 0 To intVCnt / 2 - 1              'For LWPoly 2 - 1 else 3 -1
           
      
      If intCrdCnt < intVCnt / 2 - 1 Then
        If objPline.GetBulge(intCrdCnt) = 0 Then
          varCord = objPline.Coordinate(intCrdCnt)
          varNext = objPline.Coordinate(intCrdCnt + 1)
          
          'computes a simple Pythagorean length
          dblTemp = dblTemp + Sqr(((varCord(0) - varNext(0)) ^ 2) + ((varCord(1) - varNext(1)) ^ 2))
          
                    
        Else
          'If there is a bulge we need to get an arc length
          varCord = objPline.Coordinate(intCrdCnt)
          varNext = objPline.Coordinate(intCrdCnt + 1)
          dblChord = Sqr(((varCord(0) - varNext(0)) ^ 2) + ((varCord(1) - varNext(1)) ^ 2))
          
          'Bulge is the tangent of 1/4 of the included angle between
          'vertices. So we reverse the process to get the included angle
          dblInclAng = Atn(Abs(objPline.GetBulge(intCrdCnt))) * 4
          dblAng = (dblInclAng / 2) - ((Atn(1) * 4) / 2)
          dblRad = (dblChord / 2) / (Cos(dblAng))
          dblArc = dblInclAng * dblRad
          dblTemp = dblTemp + dblArc
        End If
      End If
      
    Next intCrdCnt
      
    'WEERGEVEN LENGTE IN FUNCTIEAANROEP
    LengtePolyline2 = dblTemp
    
End Function

Attribute VB_Name = "M_BerekenRollengte"
'Public lengte As Double
Public InvoerLengte As Double
Public Stoppen As Boolean
Public lengtevanpoly As Double
Public vSnijpunt As Variant

Public Sub BerekenRollengte()
    MsgBox "DEZE ROUTINE IS BESCHADIGD VRIJDAG 21 MAART 2003"
    MsgBox "dus verwijderen !!! (ebr 27 mei 2004)"
   
    ' ------------------------------------------------------------------------------
    ' BEPALEN LAATSTE GROEP-NUMMER (UIT LAYER)EN AANMAKEN NIEUWE LAYER
    ' ------------------------------------------------------------------------------
    
    SchrijfLogFile ("[1]   BEPALEN LAATSTE GROEP-NUMMER (UIT LAYER)EN AANMAKEN NIEUWE LAYER")

    Dim LaagObj As AcadLayer
    Dim sLaagNaam As String
    Dim sLaagNummer As String
    Dim iLaagNummer As String
    Dim iHoogsteNummer As Integer
    Dim sNwLaagnaam As String

    For Each LaagObj In ThisDrawing.Layers
        sLaagNaam = UCase(LaagObj.Name)
        If Left$(sLaagNaam, 6) = "GROEP_" Then

            sLaagNummer = Right(sLaagNaam, Len(sLaagNaam) - 6)
            If Val(sLaagNummer) <> sLaagNummer Then
                MsgBox "Laag " & sLaagNummer & " bevat een verkeerd nummer.", vbCritical, "Let op"
                End
            Else
                iLaagNummer = sLaagNummer
                If iLaagNummer > iHoogsteNummer Then iHoogsteNummer = iLaagNummer
            End If

        End If
    Next LaagObj

    'GROEPSNUMMER OPHOGEN MET 1:
    If iLaagNummer = "" Then iLaagNummer = 0
    
    'NIEUWE LAAGNUMMER
    iLaagNummer = iHoogsteNummer + 1
    sLaagNummer = str(iLaagNummer)
    
    Dim AantalNullen As Integer
    If Len(sLaagNummer) > 3 Then MsgBox "Meer dan 99 groepsnummers in de laagnaam Groep_QQ. >> Purge de lagen.", vbCritical, "Let op": End
    
    
    ' ------------------------------------------------------------------------------
    ' LAAGNAAM SAMENSTELLEN
    ' ------------------------------------------------------------------------------
    
    sNwLaagnaam = "groep_" & String(3 - Len(sLaagNummer), "0") & iLaagNummer
    'MsgBox "Laag wordt: " & sNwLaagnaam
    
    ' ------------------------------------------------------------------------------
    ' LAAG KLEUR BEPALEN
    ' ------------------------------------------------------------------------------
    
    

    'LAAG AANMAKEN:

    Dim NwLaagObj As Object
    Set NwLaagObj = ThisDrawing.Layers.Add(sNwLaagnaam)
    
    'Kleur bepalen
    
    'oorspronkelijk:
    'nwLaagObj.Color = acYellow
    'nieuw:
    
    Dim KleurNo As Integer
    On Error Resume Next
    
    'MsgBox "Vorige laag-groep: " & "groep_" & iHoogsteNummer
    
    KleurNo = ThisDrawing.Layers.Item("groep_" & iHoogsteNummer).Color
    If Err Then Err.Clear
    
    If KleurNo = 2 Then
        NwLaagObj.Color = acGreen
    Else
        NwLaagObj.Color = acYellow
    End If
    
    
   

    

    ' ---------------------------------------------------------------------
    ' LAAG AANMAKEN EN AKTIEF MAKEN
    ' ---------------------------------------------------------------------
    SchrijfLogFile ("[2]   LAAG AKTIEF MAKEN")

    ThisDrawing.ActiveLayer = NwLaagObj

    ' AanmakenLaag(laagnaam,kleur,True)
    
    ' ---------------------------------------------------------------------
    ' INVOEREN TOTALE LEIDINGLENGTE)
    ' ---------------------------------------------------------------------
    SchrijfLogFile ("[3]   INVOEREN TOTALE LEIDINGLENGTE)")

    'Dim Invoerlengte As Double 'public maken
    Dim Lengte As Double       'public maken
    Dim sInvoerlengte As String

    On Error Resume Next
    'listboxen verwijderd 24 feb 2003
    'If F_Main.ListBox6.Text <> "" Then
    '   sInvoerlengte = ListBox6.Text
    'Else
        'If F_Main.ListBox5.Text <> "" Then
        '    sInvoerlengte = F_Main.ListBox5.Text
        'Else
            If F_Main.CheckBox1.Value = True Then sInvoerlengte = InputBox("Voer rollengte in (meters).", "Invoer lengte")
        'End If
    'End If

    'MsgBox sInvoerlengte
    Dim pos As Integer
    pos = InStr(1, sInvoerlengte, ".")
    If pos <> 0 Then MsgBox "Gebruik een komma, maar geen punt.", vbExclamation, "Let op": End
    
    InvoerLengte = sInvoerlengte

    SchrijfLogFile ("   Invoerlengte (cm)=" & InvoerLengte)
    InvoerLengte = InvoerLengte * 100

    If Err Then MsgBox "Geen juiste lengte opgegeven.", vbCritical, "Leidingleg-programma": End
    SchrijfLogFile ("   Invoerlengte (m)=" & InvoerLengte)

    

    ' ----------------------------------------------------------------------------
    ' SELECTEREN POLYLINE:
    '
    ' SELECTEREN VAN DE AANVOER-POLYLINE T.B.V. HET BEREKENEN
    ' VAN DE LENGTE VAN HET LEGPATROON
    '((((INCLUSIEF DE LENGTE
    ' VAN DE RETOURLEIDING (NA BEPALEN SNIJPUNT)))??
    ' ----------------------------------------------------------------------------
    SchrijfLogFile ("[4]   SELECTEREN POLYLINE (aanvoer) en plaatsen pijl-block")

    'ThisDrawing.SetVariable "PDMODE", 35    'Laat snijpunt zien.

    If F_Main.CheckBox2.Value = True Then

        Dim RetourObj As Object
        On Error Resume Next
        ThisDrawing.Utility.GetEntity RetourObj, basePnt, "Selecteer de aanvoer-leiding."
        If RetourObj.EntityName <> "AcDbPolyline" Then MsgBox "Geen polyline geselecteerd.", vbCritical, "Let op": Exit Sub
        If Err <> 0 Then
            Err.Clear
            MsgBox "Verkeerd geselecteerd"
            End
        End If

        RetourObj.Layer = sNwLaagnaam
        RetourObj.Color = acByLayer
        RetourObj.Highlight True


        'BEREKENEN LENGTE VAN LWT-POLYLINE

        Lengte = LengtePolyline2(RetourObj)
        SchrijfLogFile ("     lengte van geselecteerde polyline=" & Lengte)



        'PLAATSEN BLOCK-PIJL
        'OPVRAGEN BEGINPUNT VAN LWTPOLYLINE EN AANGEVEN VAN PLAATS VERDELER

        'VOORGAANDE PIJLEN (BLOCKS) VERWIJDEREN
        Dim element As Object
        For Each element In ThisDrawing.ModelSpace
            If element.EntityName = "AcDbBlockReference" Then
                If UCase(element.Name) = "PIJL" Then
                    element.Erase
                End If
            End If
        Next element
        ThisDrawing.Regen (True)

        'OPVRAGEN BEGINPUNT VAN POLYLINE EN HIEROP PIJL PLAATSEN
        Dim coord As Variant    'vertex-array
        Dim intVCnt As Integer  'vertex-counter
        Dim varVert As Variant  'vertex

        coord = RetourObj.Coordinates
        'MsgBox coord(0) & ", " & coord(1)

        Dim BlockObj As AcadBlockReference
        Dim Pins(0 To 2) As Double
        'OPVRAGEN BEGINPUNT LWT-POLYLINE
        Pins(0) = coord(0)
        Pins(1) = coord(1)
        Pins(2) = 0
        Set BlockObj = ThisDrawing.ModelSpace.InsertBlock(Pins, "pijl", 1, 1, 1, 0)
        BlockObj.Layer = "0"
        BlockObj.Update
        
        
        ' ---------------------------------------------------------------------------------
        ' BEPALEN WELKE LIJN AAN GESELECTEERDE AANVOER-POLYLINE IS VERBONDEN.
        ' ---------------------------------------------------------------------------------
        
        
        SchrijfLogFile ("[5]   BEPALEN WELKE LIJN AAN GESELECTEERDE AANVOER-POLYLINE IS VERBONDEN.")


        Dim strHandle As String
        strHandle = BepaalLijnAanEindePolyline(RetourObj)
        'MsgBox strHandle

        'berekenen lengte v.a. eerste gewone lijn:
        Dim tempObj As AcadObject
        Set tempObj = ThisDrawing.HandleToObject(strHandle)

        'tempObj = IS DE EERSTE LIJN VERBONDEN AAN AANVOER-POLY
        
        ' ---------------------------------------------------------------------------------
        ' AUTOMATISCH BEPALEN WAT DE BIJBEHORENDE RETOURLEIDING (POLYLINE)IS.
        ' ---------------------------------------------------------------------------------

        'GESELECTEERDE AANVOER-POLYLINE:    RetourObj
        'BEGINPUNT AANVOER-POLYLINE:        coord(0), coord(1), 0

         SchrijfLogFile ("[6]   AUTOMATISCH BEPALEN WAT DE BIJBEHORENDE RETOURLEIDING (POLYLINE)IS.")



        ' MAKEN SELECTIESET:

        Dim ssetObj As AcadSelectionSet
        Dim mode As Integer

        Dim Px As Double
        Dim Py As Double

        Px = coord(0)
        Py = coord(1)

        On Error Resume Next
        Set ssetObj = ThisDrawing.SelectionSets.Add("TEST_SSET")
        If Err Then
            ThisDrawing.SelectionSets.Item("TEST_SSET").Clear
            ThisDrawing.SelectionSets.Item("TEST_SSET").Delete
        End If

        mode = acSelectionSetCrossing

        Dim Tel As Integer
        'Dim sHandle As String
        Dim corner1(0 To 2) As Double
        Dim corner2(0 To 2) As Double
        Dim ssElement As Object


        Dim gpCode(0) As Integer
        Dim dataValue(0) As Variant
        gpCode(0) = 0
        dataValue(0) = "LWPOLYLINE"

        Dim groupCode As Variant, dataCode As Variant
        groupCode = gpCode
        dataCode = dataValue

        'SELECTIE WINDOW (CROSSING !) STEEDS GROTER MAKEN, TOT DE AANVOER RETOUR POLYLINE GEVONDEN IS.

''        Dim PuntObj1 As Object
''        Dim PuntObj2 As Object

        'zoomen anders geen juiste selectieset !!
        ZoomExtents
        
        Dim JuisteRetourPolyGevonden As Boolean
                

Opnieuw1:

        Tel = Tel + 1

        corner1(0) = Px - Tel: corner1(1) = Py - Tel: corner1(2) = 0
        corner2(0) = Px + Tel: corner2(1) = Py + Tel: corner2(2) = 0
        ssetObj.Select mode, corner1, corner2, groupCode, dataCode

''        Set PuntObj1 = ThisDrawing.ModelSpace.AddPoint(corner1)
''        PuntObj1.Color = tel
''        Set PuntObj2 = ThisDrawing.ModelSpace.AddPoint(corner2)
''        PuntObj2.Color = tel

        'MsgBox "teller = " & tel & "     " & "count = " & ssetObj.Count


        ' LEZEN SELECTIESET:

        If Tel > 20 Then
            ssetObj.Clear
            ssetObj.Delete
            ZoomPrevious
            MsgBox "Geen retourleiding (polyline) gevonden in laag 'Legplan' (of HOH te groot).", vbExclamation, "Let op"
            End
        End If

        If ssetObj.Count = 0 Or ssetObj.Count = 1 Then GoTo Opnieuw1

        If ssetObj.Count > 1 Then
            For Each ssElement In ssetObj
                If RetourObj.handle <> ssElement.handle Then
                        'MsgBox "gevonden retourPolyline-handle = " & ssElement.handle
                        'sHandle = element.handle
                        
''                        If ssElement.Layer <> "Legplan" Then
''                            GoTo Opnieuw1
''                        Else
''                            ssElement.Layer = sNwLaagnaam
''                            Exit For
''                        End If


                        If ssElement.Layer = "Legplan" Then
                            ssElement.Layer = sNwLaagnaam
                            ssElement.Color = acByLayer
                            JuisteRetourPolyGevonden = True
                            Exit For
                        End If
                        

                End If
            Next ssElement
            
            If JuisteRetourPolyGevonden = False Then GoTo Opnieuw1
        End If


        ssetObj.Clear
        ssetObj.Delete

        ZoomPrevious

                
        '-----------------------------------------------------------------------------------
        'BEPALEN OF DAT HET EINDPUNT OF HET BEGINPUNT VAN DE EERSTE
        'LIJN VERBONDEN IS MET HET EINDPUNT VAN DE AANVOER-POLYLINE
        'want beide richtingen moeten mogelijk zijn.
        '-----------------------------------------------------------------------------------

        For Each varVert In coord
            intVCnt = intVCnt + 1
        Next

        'OPVRAGEN EINDPUNT LWT-POLYLINE
        'MsgBox "Laatste x =" & coord(intVCnt - 2)
        'MsgBox "Laatste y =" & coord(intVCnt - 1)

        Dim PeindPoly(0 To 2) As Double
        PeindPoly(0) = coord(intVCnt - 2)
        PeindPoly(1) = coord(intVCnt - 1)
        PeindPoly(2) = 0

        Dim Afstand1 As Double
        Dim Afstand2 As Double
        Afstand1 = M_Afstand.Lengte(PeindPoly, tempObj.EndPoint)
        Afstand2 = M_Afstand.Lengte(PeindPoly, tempObj.StartPoint)

        SchrijfLogFile ("   Lengte eerste lijn verbonden aan aanvoer-polyline = " & tempObj.Length)
        Lengte = Lengte + tempObj.Length

    End If

    ' ------------------------------------------------------------------------------------
    ' BEREKENEN WELKE LIJNEN MET ELKAAR VERBONDEN ZIJN
    ' -------------------------------------------------------------------------------------

    Dim ReturnEindpunt As Variant
    Dim Beginpunt As Variant
    Dim Eindpunt As Variant
    Dim LijnGevonden As Boolean
    Dim StartpuntGevonden As Boolean
    Dim testobj As Object


    If Afstand1 < Afstand2 Then
            ReturnEindpunt = tempObj.StartPoint
            'MsgBox "Eerste lijn met eindpunt (endpoint) verbonden aan de aanvoer-polyline-eindpunt"
    Else
            ReturnEindpunt = tempObj.EndPoint
            'MsgBox "Eerste lijn met beginpunt (startpoint) verbonden aan de aanvoer-polyline-eindpunt"
    End If



    '----------------------------------------------------------------------------------------------------
    ' *** START BEREKENING LENGTE-LOOP ***
    '----------------------------------------------------------------------------------------------------
  
    'ReturnEindpunt = tempObj.EndPoint

    Set returnObj = tempObj
    returnObj.Layer = sNwLaagnaam
    returnObj.Color = acByLayer
    
    Dim bOptellen As Boolean
    Dim EindpuntLijn As Variant

opnieuw:

    LijnGevonden = False
    
   
    For Each element In ThisDrawing.ModelSpace
    If element.EntityName = "AcDbLine" Or element.EntityName = "AcDbArc" Then

        'MsgBox element.Handle
        If returnObj.handle <> element.handle Then

                Beginpunt = element.StartPoint
                Eindpunt = element.EndPoint
                'MsgBox "Zoek naar: " & ReturnEindpunt(0) & "    " & ReturnEindpunt(1)
    
                bOptellen = False

                If AFR(ReturnEindpunt(0)) = AFR(Beginpunt(0)) Then
                    If AFR(ReturnEindpunt(1)) = AFR(Beginpunt(1)) Then
                        StartpuntGevonden = True
                        bOptellen = True
                    End If
                End If
                
                If AFR(ReturnEindpunt(0)) = AFR(Eindpunt(0)) Then
                    If AFR(ReturnEindpunt(1)) = AFR(Eindpunt(1)) Then
                        StartpuntGevonden = False
                        bOptellen = True
                    End If
                End If
                
                If bOptellen = True Then
                    element.Layer = sNwLaagnaam
                    element.Color = acByLayer
                    element.Update
                    LijnGevonden = True
                    'Set ReturnObj = element
                    Set testobj = element

                    If element.EntityName = "AcDbLine" Then Lengte = Lengte + element.Length
                    If element.EntityName = "AcDbArc" Then Lengte = Lengte + element.ArcLength
                    
'''''                    If element.EntityName = "AcDbLine" Then
'''''                        'omkeren beginpunt en eindpunt van de lijn tbv aansluiten op retour.
'''''                        If StartpuntGevonden = True Then
'''''                            EindpuntLijn = element.EndPoint
'''''                            element.EndPoint = element.StartPoint
'''''                            element.StartPoint = EindpuntLijn
'''''                            StartpuntGevonden = False
'''''                            'btempStartpuntGevonden = True
'''''                        End If
'''''                    End If
                            

                    ' BEREKENEN SNIJPUNT MET RETOUR POLYLINE
                    'ORGINEEL VOOR 28 NOV 2002
                    'If F_Main.CheckBox2.Value Then Call BepalenSnijpunt1(element, RetourObj, Lengte, sNwLaagnaam)
                    
                    If F_Main.CheckBox2.Value Then Call BepalenSnijpunt1(element, ssElement, Lengte, sNwLaagnaam)
   
                End If
        End If
        
        

        'MsgBox "DE LENGTE IS : " & Lengte, vbInformation
        
'----------------------------------------------------------------------------------------------------
' ***  MELDING ALS ROLLENGTE BEHAALD IS + BEPALEN JUISTE PUNT WAARBIJ DE LENGTE OVEREENKOMT MET DE INGEVOERDE (GEWENSTE) LENGTE ***
'----------------------------------------------------------------------------------------------------

'        If F_Main.CheckBox1.Value = True Then

        If Stoppen = True Then

                'laatste gehele lijn van het legpatroon
                element.Color = acMagenta

                'Totalelengte = lengtevanpoly + Lengte
                SchrijfLogFile ("[6]   stoppen = True")
                SchrijfLogFile ("")
                SchrijfLogFile ("  ! Invoerlengte=" & InvoerLengte)
                SchrijfLogFile ("  Lengte (tot laats berekende lijn)=" & Lengte)      'Lengte van aanvoer polyline + lijns + arcs
                SchrijfLogFile ("  LengtePolylineTotSnijpunt = " & lengtevanpoly)     'public var !
                SchrijfLogFile ("  Lengte van laatste lijnstuk=" & element.Length)
                SchrijfLogFile ("")
                
                SchrijfLogFile ("  SnijpuntX=") & vSnijpunt(0)                         'public, uit snijpuntberekening anderstaande subroutine
                SchrijfLogFile ("  SnijpuntY=") & vSnijpunt(1)
                SchrijfLogFile ("  StartpuntGevonden= " & StartpuntGevonden)
                
                '-----------------------------------------------------------------
                'BEPALEN TEKENRICHTING
                '-----------------------------------------------------------------
                
                Dim EindpuntNwLijn(0 To 2) As Double
                Dim LijnObj As Object
                Dim SituatieA As Boolean
                
                Dim SnijLengte As Double    'lengte tussen beginpunt of eindpunt van de laatste lijn (element) tot het snijpunt
                                            'tot de polyline.
                                            
                If StartpuntGevonden = True Then
                    SnijLengte = M_Afstand.Lengte(element.StartPoint, vSnijpunt)
                Else
                    SnijLengte = M_Afstand.Lengte(element.EndPoint, vSnijpunt)
                End If
                
                'MsgBox "begin of eindpunt van de laatste lijn tot snijpunt aanvoerpoly = " & SnijLengte
                 SchrijfLogFile ("begin of eindpunt van de laatste lijn tot snijpunt aanvoerpoly = " & SnijLengte)
                 
                'als retourpolyline iets verschoven is dan snijlengte <> 0, anders precies 0 !
                
                '*** uitgezet op 5 dec 2002
                '*** If SnijLengte > 0 And SnijLengte < 10 Then MsgBox "Retourpolyline staat niet precies op 1x HOH naast de aanvoerpolyline."
                
                If SnijLengte < 5 Then
                    SituatieA = True
                Else
                    SituatieA = False
                End If
                
                'MsgBox "SituatieA=" & SituatieA
                SchrijfLogFile ("SituatieA=" & SituatieA)
                
                 
                '-----------------------------------------------------------------
                'AFHANKELIJK VAN DE TEKENRICHTING LAATSTE LIJN(EN) PLAATSEN
                '-----------------------------------------------------------------
                
                Dim vEindpunt As Variant
                
                'If StartpuntGevonden = True Or StartpuntGevonden = False Then
                If SituatieA = True Then
                    'SITUATIE 2
                    SchrijfLogFile ("*** SITUATIE 1 ***")

                    Dim LengteVerschil As Double
                    LengteVerschil = (Lengte + lengtevanpoly) - InvoerLengte
                    SchrijfLogFile ("Lengteverschil van de laatste lijn moet zijn:" & LengteVerschil)

                    Dim LengteVanLaatsteLijnstuk As Double
                    LengteVanLaatsteLijnstuk = element.Length - LengteVerschil
                    SchrijfLogFile ("** Lengte laatste lijnstuk moet zijn (zonder berek arcs ed): " & LengteVanLaatsteLijnstuk)
                    LengteVanLaatsteLijnstuk = LengteVanLaatsteLijnstuk - 15.7
                    LengteVanLaatsteLijnstuk = LengteVanLaatsteLijnstuk / 2
                    SchrijfLogFile ("** Lengte laatste lijnstuk juist berekend: " & LengteVanLaatsteLijnstuk)

                    If LengteVanLaatsteLijnstuk < 0 Then MsgBox "Negatieve lengte, verleng de laatste lijn tot de retourleiding !", vbInformation: End


                    '----------------------------------------------------------------------
                    '*** NIEUW
                    '----------------------------------------------------------------------
                    If StartpuntGevonden = False Then
                        'OMKEREN LAATSTE LIJN (RICHTING VERKEERD)
                        Beginpunt(0) = Eindpunt(0)
                        Beginpunt(1) = Eindpunt(1)
                        'Dim vEindpunt As Variant
                        vEindpunt = element.EndPoint
                        element.EndPoint = element.StartPoint
                        element.StartPoint = vEindpunt
                    End If


                    'PLAATSEN BEREKENDE LIJNSTUK
                    EindpuntNwLijn(0) = Beginpunt(0) + LengteVanLaatsteLijnstuk
                    EindpuntNwLijn(1) = Beginpunt(1)
                    EindpuntNwLijn(2) = 0

                    Set LijnObj = ThisDrawing.ModelSpace.AddLine(Beginpunt, EindpuntNwLijn)
                    
                    
                    LijnObj.Rotate element.StartPoint, element.Angle
                    LijnObj.Layer = sNwLaagnaam
                    LijnObj.Color = acByLayer
                    element.StartPoint = LijnObj.EndPoint
                    'Call M_InsertBlock.InsertBlock(LijnObj.EndPoint)
                   
                    
                    'OVERIGE LIJNEN PLAATSEN:
                    Dim PuntObj As AcadPoint
                    Set PuntObj = ThisDrawing.ModelSpace.AddPoint(LijnObj.EndPoint)
                    PuntObj.Color = acRed
                    
                    Set PuntObj = ThisDrawing.ModelSpace.AddPoint(LijnObj.StartPoint)
                    PuntObj.Color = acCyan
                    
                    'PLAATSEN VAN AFTAKLIJNEN:
                    If F_Main.CheckBox4 Then Call M_TekenenAftaklijnen.TekenenAftaklijnen(F_Main.ComboBox2, LijnObj.EndPoint, element.Angle)
                                       
                    
                    
                    

                Else
                    MsgBox "IN SITUATIE II NOG GEEN AFTAKLIJNEN", vbExclamation
                    SchrijfLogFile ("SituatieA=" & SituatieA)
                            
                    Dim Opening As Double
                    Opening = InvoerLengte - Lengte - lengtevanpoly
                            SchrijfLogFile ("Opening = Invoerlengte - Lengte - lengtevanpoly = " & Opening)
                            SchrijfLogFile ("Opening / 2 = " & Opening / 2)
                    LengteVanLaatsteLijnstuk = element.Length - Abs(Opening / 2)
                            SchrijfLogFile ("LengteVanLaatsteLijnstuk = " & LengteVanLaatsteLijnstuk)
                            
                    'MsgBox "lengte van laatste lijn moet worden: " & LengteVanLaatsteLijnstuk
                    SchrijfLogFile ("")
                    SchrijfLogFile ("   >>> lengte van laatste lijn moet worden: " & LengteVanLaatsteLijnstuk)
                    SchrijfLogFile ("")
                    
                    
                    'NIEUW AANGEVULD
                    'Eindpunt(0) = Beginpunt(0)
                    'Eindpunt(1) = Beginpunt(1)
                    If StartpuntGevonden = True Then
                        'OMKEREN LAATSTE LIJN (RICHTING VERKEERD)
                        Beginpunt(0) = Eindpunt(0)
                        Beginpunt(1) = Eindpunt(1)
                        'Dim vEindpunt As Variant
                        vEindpunt = element.EndPoint
                        element.EndPoint = element.StartPoint
                        element.StartPoint = vEindpunt
                    End If
                    

                    EindpuntNwLijn(0) = Eindpunt(0) - LengteVanLaatsteLijnstuk
                    EindpuntNwLijn(1) = Eindpunt(1)
                    EindpuntNwLijn(2) = 0

                    Set LijnObj = ThisDrawing.ModelSpace.AddLine(Eindpunt, EindpuntNwLijn)
                    LijnObj.Layer = sNwLaagnaam
                    LijnObj.Color = acByLayer
                    LijnObj.Rotate element.StartPoint, element.Angle

                    'OPSCHUIVEN VAN LAATSTE LIJN
                    LijnObj.Move LijnObj.EndPoint, element.StartPoint       'let op bij bovenstaande startpoint
                    'Call M_InsertBlock.InsertBlock(LijnObj.EndPoint)
                    


                    'AANPASSEN LENGTE VAN LAATSTE (OORSPRONKELIJKE) LIJN
                    element.StartPoint = LijnObj.StartPoint
                    element.Layer = "Legplan"
                    element.Color = acByLayer

                    'Call M_InsertBlock.InsertBlock(EindpuntNwLijn)



                End If

                   

                End
                'F_Main.Show
                'Exit Sub

        End If


    End If
    Next element



'----------------------------------------------------------------------------------------------
' *** EINDE BEREKENING ***
'----------------------------------------------------------------------------------------------


    If LijnGevonden = True Then
        'MsgBox "Wacht"
        Set returnObj = testobj
        If StartpuntGevonden = True Then ReturnEindpunt = returnObj.EndPoint
        If StartpuntGevonden = False Then ReturnEindpunt = returnObj.StartPoint
        LijnGevonden = False
        GoTo opnieuw
    Else

        'INDIEN DE LENGTE VAN HET GESELECTEERDE ELEMENT GELIJK IS AAN DE TOTALE LENGTE, DAN OPNIEUW BEREKENEN
        'MAAR NU VANUIT HET STARTPUNT IPV EINDPUNT VAN DE GESELECTEERDE LINE
        If Lengte = returnObj.Length Then
            MsgBox "Geen andere leidingen gevonden die aan de geselecteerde leiding verbonden zijn.", vbInformation
            ReturnEindpunt = returnObj.StartPoint
            GoTo opnieuw
        End If

        'BEREKENING IS CORRECT UITGEVOERD
        MsgBox "De totale leidinglengte is:  " & Format(Lengte / 100, "0.0") & " m" _
            & Chr(10) & Chr(13) & Chr(10) & Chr(13) & "(korter dan " & InvoerLengte / 100 & "m)", vbInformation, "Totale lengte"
        ThisDrawing.SetVariable "modemacro", "Leidinglengte = " & Format(Lengte / 100, "0.0" & m)
        ThisDrawing.Utility.Prompt "Leidinglengte = " & Format(Lengte, "0.0")
        F_Main.show
    End If


End Sub

Function AFR(getal)
    'Afronden getal
    AFR = Format(getal, "0.0")
End Function
Sub BepalenSnijpunt1(element As Object, RetourObj As Object, Lengte, sNwLaagnaam)

' -----------------------------------------------------------------------
'   BEREKENEN INTERSECTIE (SNIJPUNT) MET RETOUR-LEIDING
' -----------------------------------------------------------------------
'   RetourObj   DIT IS DE GESELECTEERDE POLYLINE (AANVOER)
'   element     DIT IS DE BETREFFENDE LIJN (LEIDING) VAN HET LEGPATROON
'   lengte      DIT IS DE BEREKENDE LENGTE VAN HET LEGPATROON (LINES EN ARCS)
'               TOT HET BETREFFENDE ELEMENT
'   DEZE ROUTINE BEPAALD HET SNIJPUNT TUSSEN DEZE TWEE ELEMENENTEN
' -----------------------------------------------------------------------


    If RetourObj.handle = element.handle Then Exit Sub
    element.Layer = sNwLaagnaam

    Dim intPoints As Variant
    intPoints = element.IntersectWith(RetourObj, acExtendThisEntity)

    Dim I As Integer, j As Integer, k As Integer
    Dim str As String
    If VarType(intPoints) <> vbEmpty Then

        For I = LBound(intPoints) To UBound(intPoints)
            'str = "Intersection Point[" & k & "] is: " & intPoints(j) & "," & intPoints(j + 1) & "," & intPoints(j + 2)
            'MsgBox str: str = ""
            I = I + 2
            j = j + 3
            k = k + 1   'geeft aantal snijpunten aan
        Next
    End If

' -----------------------------------------------------------------------
'   CONTROLE OP HET AANTAL SNIJPUNTEN
' -----------------------------------------------------------------------

    If k = 0 Then
        'MsgBox "Leiding heeft geen snijpunt met de aanvoer/ retourleiding", vbCritical
        Exit Sub
    End If
    
    If k = 1 Then
        vSnijpunt = intPoints
    End If
        

'    If k > 1 Then
'        MsgBox "Leiding heeft meerdere snijpunten met de aanvoer/ retourleiding", vbCritical
'        Exit Sub
'    End If

' --------------------------------------------------------------------------------------------
'   BEREKENEN LENGTE VAN DE POYLINE TOT HET HIERBOVEN BEREKENENDE SNIJPUNT OP DEZE POLYLINE
' --------------------------------------------------------------------------------------------

    'Dim c As Double
    Dim LengtePolylineTotSnijpunt As Double
    
    'c = LengtePolyline(RetourObj, intPoints, False)

    LengtePolylineTotSnijpunt = LengtePolyline(RetourObj, intPoints, True)
    'MsgBox "LENGTE MET SNIJPUNT:" & LengtePolylineTotSnijpunt
    'LENGTE POLYLINE TOT HET BEREKENDE SNIJPUNT + LENGTE VAN LEGPATROON


    If F_Main.CheckBox1.Value = True Then
        If InvoerLengte < (LengtePolylineTotSnijpunt + Lengte) Then
            'POINT AFBEELDEN OP HET SNIJPUNT
            'Dim PointObj As Object
            'Set PointObj = ThisDrawing.ModelSpace.AddPoint(intPoints)
            'PointObj.Update

            'Dim TekstObj As Object
            'Set TekstObj = ThisDrawing.ModelSpace.AddText("LengtePolylineTotSnijpunt=" & LengtePolylineTotSnijpunt & "    Lengte=" & Lengte, intPoints, 6)
            'MsgBox "Stoppen"
            Stoppen = True
            lengtevanpoly = LengtePolylineTotSnijpunt       'public voor de hoofdroutine!
            'End


        End If
    End If

End Sub

Attribute VB_Name = "M_TekenenAftaklijnen"
Const NegentigGraden = 1.5707963267949

Sub StartTekenenAftaklijnen()
    'DEZE SUB ALLEEN NODIG VOOR TESTDOELEINDEN VAN DE ONDERSTAANDE SUBROUTINER.
    Dim HoH As Double
    Dim Pbegin(0 To 2) As Double
    
    HoH = 10
    Pbegin(0) = 0
    Pbegin(1) = 0
    
    HOEK = 1
    
    Call TekenenAftaklijnen(HoH, Pbegin, HOEK)
End Sub

Sub TekenenAftaklijnen(HoH, Pbegin, HOEK)
    
   
    
    Dim LijnObj As AcadLine
    Dim Pstart(0 To 2) As Double
    Dim Peind(0 To 2) As Double
    
    Dim ArcObj As AcadArc
    Dim Pcenter(0 To 2) As Double
    Dim Radius As Double
    Dim Starthoek As Double
    Dim EindHoek As Double
    
    Dim LaagNaam As String
    LaagNaam = "Legplan"
    
    '-----------------------------------------------------------
    
'    'Horizontale lijnstuk
'    Pstart(0) = Pbegin(0) + 2 * HOH
'    Pstart(1) = Pbegin(1)
'
'    Peind(0) = Pbegin(0) + 50
'    Peind(1) = Pbegin(1)
'
'    Set LijnObj = ThisDrawing.ModelSpace.AddLine(Pstart, Peind)
'    LijnObj.Rotate Pbegin, Hoek
'    LijnObj.Layer = "Legplan"
    
    
    '-----------------------------------------------------------
    'Eerste Arc
    
    
    Pcenter(0) = Pbegin(0) + 2 * HoH
    Pcenter(1) = Pbegin(1) + (HoH / 2)
    Radius = HoH / 2
    Starthoek = 2 * NegentigGraden
    EindHoek = -NegentigGraden
    
    Set ArcObj = ThisDrawing.ModelSpace.AddArc(Pcenter, Radius, Starthoek, EindHoek)
    ArcObj.Rotate Pbegin, HOEK
    ArcObj.Layer = "Legplan"
   
    
    '-----------------------------------------------------------
    
    'Verticale lijnstuk
    Pstart(0) = Pbegin(0) + (1.5 * HoH)
    Pstart(1) = Pbegin(1) + (HoH / 2)
    
    Peind(0) = Pstart(0)
    Peind(1) = Pbegin(1) + (1.5 * HoH)
    Set LijnObj = ThisDrawing.ModelSpace.AddLine(Pstart, Peind)
    LijnObj.Rotate Pbegin, HOEK
    LijnObj.Layer = "Legplan"
    
    '------------------------------------------------------------------
    
    'Tweede Arc
    
    Pcenter(0) = Pbegin(0) + (HoH)
    Pcenter(1) = Pbegin(1) + (HoH * 1.5)
    Radius = HoH / 2
    Starthoek = 0
    EindHoek = NegentigGraden
    
    Set ArcObj = ThisDrawing.ModelSpace.AddArc(Pcenter, Radius, Starthoek, EindHoek)
    ArcObj.Rotate Pbegin, HOEK
    ArcObj.Layer = "Legplan"
  
    
    
    '------------------------------------------------------------------
    
    'Derde Arc
    
    Pcenter(0) = Pbegin(0) + (3 * HoH)
    Pcenter(1) = Pbegin(1) + (1.5 * HoH)
    Radius = HoH / 2
    Starthoek = NegentigGraden
    EindHoek = -NegentigGraden
    
    Set ArcObj = ThisDrawing.ModelSpace.AddArc(Pcenter, Radius, Starthoek, EindHoek)
    ArcObj.Rotate Pbegin, HOEK
    ArcObj.Layer = "Legplan"
    
    '-----------------------------------------------------------
    
    End
    

End Sub

Attribute VB_Name = "M_TrimPolyline"

'''TEST VOOR ONDERSTAANDE ROUTINE
'''Private Sub CommandButton38_Click()
'''    Dim PolyObj As AcadLWPolyline
'''    Dim p As Variant
'''
'''    Me.Hide
'''opnieuw:
'''
'''    ThisDrawing.Utility.GetEntity PolyObj, p
'''    Call M_TrimPolyline.TrimPolyline(PolyObj, p)
'''
'''    GoTo opnieuw
'''End Sub







Public Sub TrimPolyline(PolyObj As AcadLWPolyline, Psnij As Variant)
    
    'Punt (Psnij)
    'MsgBox "trimpolyline", vbInformation
    
    '-----------------------------------------------------------------------------
    'DOOR EBR 6 MEI 2004:
    'DEZE FUNCTIE TRIMT EEN POLYLINE. HET EINDE VAN POLYLINE ZAL HIERBIJ WORDEN
    'VERWIJDERD (DUS NIET VANAF BEGINPUNT)
    'HET SNIJPUNT MOET WEL "EXACT" OP DE POLYLINE LIGGEN.
    'FUNCTIE GAAT NIET GOED ALS EEN PUNT OP ARC OP DE POLYLINE GESELECTEERD WORDT
    'DUS POYLINE MAG VOOR GOEDE WERKING GEEN BULGES BEVATTEN.
    '(ECHTER, EEN POLYLINE KAN AAN HET UITEINDE NOOIT GEEN BULGE HEBBEN)
    '-----------------------------------------------------------------------------
        
    Dim varCords
    Dim t As Integer
    Dim bStoppen As Boolean
    
    Dim dHoekRad As Double
    Dim dHoekRadnw As Double
    
    Dim p1(0 To 2) As Double
    Dim p2(0 To 2) As Double
    
    
opnieuw:

    varCords = PolyObj.Coordinates
    'MsgBox UBound(varCords)
    
    'INDIEN POLYLINE UIT SLECHTS 1 LIJN BESTAAT, DAN EINDPUNT GELIJKMAKEN AAN SNIJPUNT
    If UBound(varCords) < 4 Then
        'MsgBox "te trimmen polyline bestaat uit 1 lijnsegment (0 t/m 3 is 4 vertexen)"
        varCords(UBound(varCords) - 1) = Psnij(0)
        varCords(UBound(varCords) - 0) = Psnij(1)
        
        PolyObj.Coordinates = varCords
        'PolyObj.Color = acRed
        Exit Sub
    End If
    
    
    'HOEK BEPALEN VAN LAATSTE VAN POLYLINE
    'EINDPUNT VAN POLYLINE GELIJK MAKEN AAN SNIJPUNT EN
    'OPNIEUW HOEK OPVRAGEN
    
    p1(0) = varCords(UBound(varCords) - 3)
    p1(1) = varCords(UBound(varCords) - 2)
    p2(0) = varCords(UBound(varCords) - 1)
    p2(1) = varCords(UBound(varCords) - 0)
    
    dHoekRad = ThisDrawing.Utility.AngleFromXAxis(p1, p2)
    
    varCords(UBound(varCords) - 1) = Psnij(0)
    varCords(UBound(varCords) - 0) = Psnij(1)
    
    p1(0) = varCords(UBound(varCords) - 3)
    p1(1) = varCords(UBound(varCords) - 2)
    p2(0) = varCords(UBound(varCords) - 1)
    p2(1) = varCords(UBound(varCords) - 0)
    
    dHoekRadnw = ThisDrawing.Utility.AngleFromXAxis(p1, p2)


    'INDIEN HOEKEN NIET GELIJK, DAN COORDINATEN NIET AANPASSEN EN STOPPEN
    'ANDERS LAATSTE X EN Y-WAARDE VAN POLILYNE VERWIJDEREN EN OPNIEUW
    
    'LET OP: ROUND, ANDERS TE NAUWKEURIG !
    
    If Round(dHoekRad, 0) = Round(dHoekRadnw, 0) Then
        bStoppen = True
    Else
        'laatste x en y waarde verwijderen
        ReDim Preserve varCords(UBound(varCords) - 2)

        p1(0) = varCords(UBound(varCords) - 3)
        p1(1) = varCords(UBound(varCords) - 2)
        p2(0) = varCords(UBound(varCords) - 1)
        p2(1) = varCords(UBound(varCords) - 0)
    End If
    

    PolyObj.Coordinates = varCords
    'PolyObj.Color = acGreen
    
    If bStoppen = True Then Exit Sub
    GoTo opnieuw
    

End Sub

'manier 1:
'Dim Points
'Points = varCords
'ReDim Preserve Points(UBound(Points) - 2)

                        
'    Dim PolyObj2 As AcadLWPolyline
'    Set PolyObj2 = ThisDrawing.ModelSpace.AddLightWeightPolyline(varCords)
'    PolyObj2.Color = acYellow
'    PolyObj2.Update

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True


Private Sub AcadDocument_EndCommand(ByVal CommandName As String)
    'If UserForm1.Visible = True Then
        If F_LengteMonitor.Image1.Visible = True Then Call F_LengteMonitor.MeetLengte
    'End If
End Sub
