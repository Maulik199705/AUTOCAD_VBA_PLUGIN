Attribute VB_Name = "AfmetingenUnits"
Attribute VB_Base = "0{6E915550-2DB4-4553-A547-C78F4638B7CF}{F7B9A39D-57ED-4716-9538-0219BD6FCE92}"
Attribute VB_GlobalNameSpace = False
Attribute VB_Creatable = False
Attribute VB_PredeclaredId = True
Attribute VB_Exposed = False
Attribute VB_TemplateDerived = False
Attribute VB_Customizable = False
'afmetingen units aangepast op 17-11-2006 G.C.Haak
'maakt gebruik van HERZ.txt ' KMV.txt ' LT.txt  ' LT-N.txt ' LTVK.txt ' LTS.txt ' LTS-N.txt ' RUBK-R.txt
' RUB-R.txt ' RU-EE.txt  ' RUH-R.txt ' RUH-N.txt ' RUV.txt ' RU-WK.txt ' RU-WW.txt ' VSKO.txt

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
'EntryCount = 0
ListBox2.Clear
Label4.Visible = False
Label5.Visible = False
Label6.Visible = False
Label7.Visible = False
Melding.Visible = False
ListBox1.AddItem ("HERZ")
ListBox1.AddItem ("KMV")
ListBox1.AddItem ("LT")
ListBox1.AddItem ("LT-N")
ListBox1.AddItem ("LT-VK")
ListBox1.AddItem ("LTS")
ListBox1.AddItem ("LTS-N")
ListBox1.AddItem ("RUBK-R") '
ListBox1.AddItem ("RUB-R/T")
ListBox1.AddItem ("RUB-S")
ListBox1.AddItem ("RU-EE")
ListBox1.AddItem ("RUH-R/T")
ListBox1.AddItem ("RUH-S")
ListBox1.AddItem ("RUH-N")
ListBox1.AddItem ("RUV")
ListBox1.AddItem ("RU-WK")
ListBox1.AddItem ("RU-WW")
ListBox1.AddItem ("VSKO")

ListBox3.AddItem ("1 groeps")
ListBox3.AddItem ("2 groepen")
ListBox3.AddItem ("3 groepen")
ListBox3.AddItem ("4 groepen")
ListBox3.AddItem ("5 groepen")
ListBox3.AddItem ("6 groepen")
ListBox3.AddItem ("7 groepen")
ListBox3.AddItem ("8 groepen")
ListBox3.AddItem ("9 groepen")
ListBox3.AddItem ("10 groepen")
ListBox3.AddItem ("11 groepen")
ListBox3.AddItem ("12 groepen")
ListBox3.AddItem ("13 groepen")
ListBox3.AddItem ("14 groepen")
ListBox3.AddItem ("15 groepen")
ListBox3.AddItem ("16 groepen")
ListBox3.AddItem ("17 groepen")
ListBox3.AddItem ("18 groepen")
ListBox3.AddItem ("19 groepen")
ListBox3.AddItem ("20 groepen")
End Sub
Private Sub CancelButton1_Click()
Unload Me
End Sub
Private Sub ListBox1_Click()

If ListBox1.Value = "HERZ" Then bestand10 = "c:\acad2002\dwg\herz.txt" 'Call herz
If ListBox1.Value = "KMV" Then bestand10 = "c:\acad2002\dwg\kmv.txt" ' Then Call kmv
If ListBox1.Value = "LT" Then bestand10 = "c:\acad2002\dwg\lt.txt" 'Then Call lt
If ListBox1.Value = "LT-N" Then bestand10 = "c:\acad2002\dwg\lt-n.txt" 'Then Call lt
If ListBox1.Value = "LT-VK" Then bestand10 = "c:\acad2002\dwg\lt-vk.txt" 'Then Call ltvk
If ListBox1.Value = "LTS" Then bestand10 = "c:\acad2002\dwg\lts.txt" 'Then Call lts
If ListBox1.Value = "LTS-N" Then bestand10 = "c:\acad2002\dwg\lts-n.txt" 'Then Call ltsn
If ListBox1.Value = "RUBK-R" Then bestand10 = "c:\acad2002\dwg\rubk-r.txt" 'Then Call rubk
If ListBox1.Value = "RUB-R/T" Then bestand10 = "c:\acad2002\dwg\rub-r.txt" 'Then Call rubr
If ListBox1.Value = "RUB-S" Then bestand10 = "c:\acad2002\dwg\rub-s.txt" 'Then Call rubr
If ListBox1.Value = "RU-EE" Then bestand10 = "c:\acad2002\dwg\ru-ee.txt" 'Then Call ruee
If ListBox1.Value = "RUH-R/T" Then bestand10 = "c:\acad2002\dwg\ruh-r.txt" 'Then Call ruhr
If ListBox1.Value = "RUH-S" Then bestand10 = "c:\acad2002\dwg\ruh-s.txt" 'Then Call ruhr
If ListBox1.Value = "RUH-N" Then bestand10 = "c:\acad2002\dwg\ruh-n.txt" 'Then Call ruhn
If ListBox1.Value = "RUV" Then bestand10 = "c:\acad2002\dwg\ruv.txt" 'Then Call ruv
If ListBox1.Value = "RU-WK" Then bestand10 = "c:\acad2002\dwg\ru-wk.txt" 'Then Call ruwk
If ListBox1.Value = "RU-WW" Then
    bestand10 = "c:\acad2002\dwg\ru-ww.txt"
    Label5.Caption = "B352 t/m B370"
    Label7.Caption = "50-40"
    Label4.Visible = True
    Label5.Visible = True
    Label6.Visible = True
    Label7.Visible = True
    Melding.Visible = True
End If
If ListBox1.Value = "VSKO" Then bestand10 = "c:\acad2002\dwg\vsko.txt" 'Then Call vsko
If Not ListBox3.ListIndex < 0 Then ListBox2.ListIndex = ListBox3.ListIndex

Call lees(bestand10)
End Sub
Sub lbvals()
Label4.Visible = False
Label5.Visible = False
Label6.Visible = False
Label7.Visible = False
Melding.Visible = False
End Sub
Private Sub ListBox3_Click()
   If Not ListBox1.ListIndex < 0 Then
       Melding.Visible = False
       ListBox2.ListIndex = ListBox3.ListIndex
   Else
       Melding.Visible = True
   End If
End Sub
Sub lees(bestand10)

ListBox2.Clear
If bestand10 <> "c:\acad2002\dwg\ru-ww.txt" Then Call lbvals
Const ForReading = 1, ForWriting = 2, ForAppending = 8
Const TristateUseDefault = -2, TristateTrue = -1, TristateFalse = 0

Dim fs, a, vullistbox2
Set fs = CreateObject("Scripting.FileSystemObject")
Set a = fs.OpenTextFile(bestand10, ForReading, False)


Do While a.AtEndOfLine <> True
    vullistbox2 = a.ReadLine
   AfmetingenUnits.ListBox2.AddItem (vullistbox2)
Loop
a.Close 'sluiten van tekstbestand
End Sub

Attribute VB_Name = "Checklayer"
Sub Checklayer()
On Error Resume Next

'als groeps- of wandlayer leeg is dan verwijderen
'uitgevoerd na knop indrukken
Dim layerObj As Object
For Each layerObj In ThisDrawing.Layers
  mystr = Left(layerObj.Name, 5)
  If mystr = "groep" Or mystr = "GROEP" Or mystr = "wand" Or mystr = "WAND" Then
    If layerObj.Length = 0 Then layerObj.Delete
 End If 'mystr
Next layerObj
Update
End Sub

Attribute VB_Name = "Module1"
Sub Vloermuur()
frmVloermuur.Show
End Sub
Sub montageblok()
MontageblokForm.Show
End Sub
Sub splitsen()
frmSplitsen.Show
End Sub
Sub lvblokken()
blokken.Show
End Sub
Sub AfmetingenUnit()
AfmetingenUnits.Show
End Sub
Sub layerlijst()
frmLayerlijst.Show
End Sub
Sub Ruimtenaam()
frmRuimtenaam.Show
End Sub
Sub dwgcheck()
frmDrawingcheck.Show
End Sub

Attribute VB_Name = "MontageblokForm"
Attribute VB_Base = "0{74DC11E5-5418-4ED7-994E-2E8E631A3FF9}{C9FE4FDE-60B3-4924-B9DD-38FEC8D57CF5}"
Attribute VB_GlobalNameSpace = False
Attribute VB_Creatable = False
Attribute VB_PredeclaredId = True
Attribute VB_Exposed = False
Attribute VB_TemplateDerived = False
Attribute VB_Customizable = False


#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000



Private Sub CommandButton2_Click()
    Dim RetObj As Object
    Dim Pbase As Variant
 On Error Resume Next
 
MontageblokForm.Hide

opnieuw5:

ThisDrawing.Utility.GetEntity RetObj, Pbase, "Selecteer een blok."

 If RetObj.ObjectName = "AcDbBlockReference" Then
      If RetObj.Name = "Montagetsblok" Then
      Set symbool = RetObj
        If symbool.HasAttributes Then
        attributen = symbool.GetAttributes
        For j = LBound(attributen) To UBound(attributen)
        Set attribuut = attributen(j)
        
        If Err Then
          MontageblokForm.Show
        TextBox1 = TextBox1 - 1
        Exit Sub
        End If
        
        attribuut.textstring = TextBox1 'REGELUNITNUMMER
        
        
       Next j
       
        End If
      End If
      End If

TextBox1 = TextBox1 + 1
GoTo opnieuw5
End Sub

Sub ESelectOnScreen()
  
End Sub
Private Sub TextBox1_Change()
On Error Resume Next
Dim C As Double
C = TextBox1

If Err Then
   TextBox1 = Clear
  Exit Sub
  End If
End Sub

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
  Call zoekblok3
  
  Dim lognaam
   lognaam = ThisDrawing.GetVariable("loginname")
   lognaam = UCase(lognaam)
   If lognaam = "GERARD" Then
   TextBox2.Visible = True
   CheckBox5.Visible = True
   'CheckBox6.Visible = True
   End If

End Sub

Private Sub CancelButton_Click()
Call zoekblok2
 groepinvoerBox1.Value = Clear
 groepinvoerBox2.Value = Clear
groepinvoerBox2.SetFocus
Label2.Caption = Clear
Unload Me
Dim newLayer As AcadLayer
Set newLayer = ThisDrawing.Layers.Add("3")
ThisDrawing.ActiveLayer = newLayer
Update
'ThisDrawing.SendCommand "_vbaunload" & vbCr & "montageblok.dvb" & vbCr
End Sub

Private Sub groepinvoerBox1_Change()
Dim a As Double
On Error Resume Next
a = groepinvoerBox1.Text
If groepinvoerBox1 <> "" And groepinvoerBox2 <> "" Then PlaatsButton.Enabled = True
If groepinvoerBox1.Value = Clear Then Call ThisDrawing.imagelijst1
If a = 1 Then Call ThisDrawing.imagelijst2
If a = 2 Then Call ThisDrawing.imagelijst3
If a = 3 Then Call ThisDrawing.imagelijst4
If a = 4 Then Call ThisDrawing.imagelijst5
If a = 5 Then Call ThisDrawing.imagelijst6
If a = 6 Then Call ThisDrawing.imagelijst7
If a = 7 Then Call ThisDrawing.imagelijst8
If a = 8 Then Call ThisDrawing.imagelijst9
If a = 9 Then Call ThisDrawing.imagelijst10
If a = 10 Then Call ThisDrawing.imagelijst11
If a = 11 Then Call ThisDrawing.imagelijst12
If a = 12 Then Call ThisDrawing.imagelijst13
If a = 13 Then Call ThisDrawing.imagelijst14
If a = 14 Then Call ThisDrawing.imagelijst15
If a = 15 Then Call ThisDrawing.imagelijst16
If a = 16 Then Call ThisDrawing.imagelijst17
If a = 17 Then Call ThisDrawing.imagelijst18
If a = 18 Then Call ThisDrawing.imagelijst19
If a = 19 Then Call ThisDrawing.imagelijst20
If a = 20 Then Call ThisDrawing.imagelijst21

If Err Then
   groepinvoerBox1 = Clear
   PlaatsButton.Enabled = False
  Exit Sub
  End If

If a > 20 Then
   MsgBox "Groter dan 20 groepen is niet toegestaan..!!!!", vbCritical
   groepinvoerBox1 = Clear
   groepinvoerBox1.SetFocus
End If
   
If a > -1 And a < 1 Then
    groepinvoerBox1 = Clear
    groepinvoerBox1.SetFocus
End If
   
End Sub
Private Sub groepinvoerBox2_Change()
Dim b As Double
On Error Resume Next
groepinvoerBox2.SetFocus

b = groepinvoerBox2.Text
C = "Regelunit" & " " & b
Label2.Caption = C

If Err Then
   groepinvoerBox2 = Clear
   Label2.Caption = Clear
   PlaatsButton.Enabled = False
   CommandButton1.Enabled = False
  Exit Sub
  End If

If b > -1 And b < 1 Then
    groepinvoerBox2 = Clear
    groepinvoerBox2.SetFocus
End If

If groepinvoerBox2 <> "" Then
    CommandButton1.Enabled = True
    CommandButton1.SetFocus
Else
    CommandButton1.Enabled = False
End If

If groepinvoerBox1 <> "" And groepinvoerBox2 <> "" Then PlaatsButton.Enabled = True
End Sub
Private Sub CommandButton1_Click()
Call zoekblok1
End Sub
Sub zoekblok1()
For Each element20 In ThisDrawing.ModelSpace
      If element20.ObjectName = "AcDbBlockReference" Then
      'If UCase(element20.Name) = "MAT_SPE_ZD" Or UCase(element20.Name) = "MAT_SPE_PE" Then
      If element20.Name = "Mat_spe_ZD" Or element20.Name = "Mat_spe_PE" Or element20.Name = "Mat_spe_PE800" _
      Or element20.Name = "Mat_spe_ALU" Or element20.Name = "Mat_spe_ZDringleiding" Or element20.Name = "Mat_spe_PEringleiding" Or _
      element20.Name = "Mat_spe_ALUringleiding" Or element20.Name = "Mat_spe_FLEX" Or element20.Name = "Mat_spe_ZD_1627" Or _
      element20.Name = "Mat_spe_ZD_1627500" Then

      
      Set symbool = element20
        
        If symbool.HasAttributes Then
        attributen = symbool.GetAttributes
        For I = LBound(attributen) To UBound(attributen)
        Set attribuut = attributen(I)
          If attribuut.TagString = "RNU" Then
               rnc = attribuut.textstring
               rnc2 = Len(rnc)
               If rnc2 = 1 Then CheckBox3.Value = True
           End If
             If Val(groepinvoerBox2) = rnc Then
              b0 = element20.InsertionPoint
              For l = LBound(attributen) To UBound(attributen)
              Set attribuut = attributen(l)
              element20.Highlight (True)
                          
          If attribuut.TagString = "REGELUNITTYPE" Then
          rgl = attribuut.textstring 'TYPE REGELUNIT
          rgl2 = Split(rgl, " ")
          rgl3 = Len(rgl2(1))
           If rgl3 > 2 Then
                'MsgBox "meer dan 2 stuks"
              rgl4 = Split(rgl2(1), "/")
              groepinvoerBox1 = rgl4(0)
           End If
           
           If rgl3 = 1 Or rgl3 = 2 Then
           'MsgBox "klopt 2 stuks"
              rgl4 = Val(rgl2(1))
              groepinvoerBox1 = rgl4
            End If
          End If 'regelunittype
              Next l
                
         End If
       Next I
       
      End If
      End If
      End If
  Next element20
 Update
 
If groepinvoerBox1 = "" Then
   a = "Het bloklogo van regelunit " & groepinvoerBox2 & " is er niet."
   MsgBox a, vbExclamation
     groepinvoerBox2 = Clear
     groepinvoerBox2.SetFocus
     'Unload Me
     Exit Sub
     
 End If
 

 Dim b1(0 To 2) As Double
  b1(0) = b0(0) - 1500 '1000
  b1(1) = b0(1) - 400  '500
  b1(2) = 0
 
 Dim b2(0 To 2) As Double
  b2(0) = b0(0) + 500
  b2(1) = b0(1) + 1000 '750
  b2(2) = 0
  
  
''''  Dim lognaam
''''  lognaam = ThisDrawing.GetVariable("loginname")
''''  lognaam = UCase(lognaam)
''''  If lognaam = "GERARD" And CheckBox5.Value = False Then
''''  ZoomWindow b1, b2
''''  End If
  
  If CheckBox5.Value = False Then ZoomWindow b1, b2
   
Call PlaatsButton_Click

End Sub
Sub zoekblok2()
For Each element20 In ThisDrawing.ModelSpace
      If element20.ObjectName = "AcDbBlockReference" Then
      'If UCase(element20.Name) = "MAT_SPE_ZD" Or UCase(element20.Name) = "MAT_SPE_PE" Then
       If element20.Name = "Mat_spe_ZD" Or element20.Name = "Mat_spe_PE" Or element20.Name = "Mat_spe_PE800" _
      Or element20.Name = "Mat_spe_ALU" Or element20.Name = "Mat_spe_ZDringleiding" Or element20.Name = "Mat_spe_PEringleiding" Or _
      element20.Name = "Mat_spe_ALUringleiding" Or element20.Name = "Mat_spe_FLEX" Then
      Set symbool = element20
        If symbool.HasAttributes Then
        attributen = symbool.GetAttributes
        For I = LBound(attributen) To UBound(attributen)
        Set attribuut = attributen(I)
          If attribuut.TagString = "RNU" Then rnc = Val(attribuut.textstring)
             If Val(groepinvoerBox2) = rnc Then element20.Highlight (False)
         Next I
       
      End If
      End If
      End If
  Next element20
 Update
End Sub
Sub zoekblok3()
For Each element20 In ThisDrawing.ModelSpace
      If element20.ObjectName = "AcDbBlockReference" Then
      'If UCase(element20.Name) = "MAT_SPE_ZD" Or UCase(element20.Name) = "MAT_SPE_PE" Then
       If element20.Name = "Mat_spe_ZD" Or element20.Name = "Mat_spe_PE" Or element20.Name = "Mat_spe_PE800" _
      Or element20.Name = "Mat_spe_ALU" Or element20.Name = "Mat_spe_ZDringleiding" Or element20.Name = "Mat_spe_PEringleiding" Or _
      element20.Name = "Mat_spe_ALUringleiding" Or element20.Name = "Mat_spe_FLEX" Then
      Set symbool = element20
        If symbool.HasAttributes Then
        attributen = symbool.GetAttributes
        For I = LBound(attributen) To UBound(attributen)
        Set attribuut = attributen(I)
          If attribuut.TagString = "RNU" Then
               rnc = attribuut.textstring
               rnc2 = Len(rnc)
               If rnc2 = 1 Then CheckBox3.Value = True
           End If
             
           Next I
       
      End If
      End If
      End If
  Next element20
End Sub
Private Sub PlaatsButton_Click()
Call Schaal(scaal)
On Error Resume Next

 
 Dim pb1 As Variant
 Dim pe2(0 To 2) As Double
 Dim blockRefObj As AcadBlockReference
 Dim element As AcadEntity
 Dim nieuwelement As AcadEntity
 ThisDrawing.ObjectSnapMode = False

If groepinvoerBox1 = "1" Then
     MsgBox "Een 1 groeps montageblok vermelden we niet op de tekening..!!!!", vbCritical
     groepinvoerBox1 = Clear
     groepinvoerBox1.SetFocus
     PlaatsButton.Enabled = False
     Exit Sub
     End If
     

Dim newLayer As AcadLayer
Set newLayer = ThisDrawing.Layers.Add("MONTAGEBLOK")
ThisDrawing.ActiveLayer = newLayer
Update

If MontageblokForm.TextBox2 <> "" Then scaal = MontageblokForm.TextBox2
 MontageblokForm.Hide
 On Error Resume Next
 Dim bestand As String
 bestand = "c:\acad2002\dwg\Montagetsblok.dwg"
 pb1 = ThisDrawing.Utility.GetPoint(, "Plaats startpunt")
   
'''''   If OptionButton1.Value = True Or OptionButton2.Value = True Then
'''''    Dim ssetObj As AcadSelectionSet
'''''    Set ssetObj = ThisDrawing.SelectionSets.Add("SSET")
'''''    pbz = ThisDrawing.Utility.GetPoint(, "Plaats eindpunt")
'''''    ssetObj.Select acSelectionSetCrossing, pbz, pb1
'''''    ssetObj.Erase
'''''   End If
 
 
 Set blockRefObj = ThisDrawing.ModelSpace.InsertBlock(pb1, bestand, scaal, scaal, 1, 0)
 
 If OptionButton1.Value = True Then  'autonummering
    ' Get the attributes for the block reference
    Dim varAttributes As Variant
    varAttributes = blockRefObj.GetAttributes

    ' Move the attribute tags and values into a string to be displayed in a Msgbox
    Dim strAttributes As String
    Dim I As Integer
    For I = LBound(varAttributes) To UBound(varAttributes)
        strAttributes = strAttributes & "  Tag: " & varAttributes(I).TagString & _
                        "   Value: " & varAttributes(I).textstring & "    "
    Next
    'MsgBox "The attributes for blockReference " & blockrefobj.Name & " are: " & strAttributes, , ""

     ' Change the value of the attribute
    ' Note: There is no SetAttributes. Once you have the variant array, you have the objects.
    ' Changing them changes the objects in the drawing.
   'varAttributes(0).textstring = "NEW VALUE!"
  varAttributes(0).textstring = groepinvoerBox1
 End If 'autonummering
 
 If OptionButton2.Value = True Then  'autonummering
    ' Get the attributes for the block reference
    'Dim varAttributes As Variant
    varAttributes = blockRefObj.GetAttributes

    ' Move the attribute tags and values into a string to be displayed in a Msgbox
    'Dim strAttributes As String
    'Dim I As Integer
    For I = LBound(varAttributes) To UBound(varAttributes)
        strAttributes = strAttributes & "  Tag: " & varAttributes(I).TagString & _
                        "   Value: " & varAttributes(I).textstring & "    "
    Next
    'MsgBox "The attributes for blockReference " & blockrefobj.Name & " are: " & strAttributes, , ""

     ' Change the value of the attribute
    ' Note: There is no SetAttributes. Once you have the variant array, you have the objects.
    ' Changing them changes the objects in the drawing.
   'varAttributes(0).textstring = "NEW VALUE!"
  varAttributes(0).textstring = "1"
 End If 'autonummering
 
 
 
 
 
 
 If Err Then
    ThisDrawing.ObjectSnapMode = True
    groepinvoerBox1.SetFocus
    MontageblokForm.Show
    Exit Sub
    End If

 blockRefObj.Update
 
  
  a = groepinvoerBox1 'aantal groepen
  b = a - 1  'aantal groepen -1
  qw = b
  
  If OptionButton2.Value = True Then
  a = groepinvoerBox1 'aantal groepen
  b = a - 1  'aantal groepen -1
  qw = 2
  End If
  
  
  
 For I = 1 To b
      ' Change the value of the attribute
    ' Note: There is no SetAttributes. Once you have the variant array, you have the objects.
    ' Changing them changes the objects in the drawing.
    If OptionButton1.Value = True Then varAttributes(0).textstring = qw
    If OptionButton2.Value = True Then varAttributes(0).textstring = qw
    
 pe2(0) = pb1(0) - ((I * 44.6) * scaal)
 pe2(1) = pb1(1)
 pe2(2) = 0
 Set nieuwelement = blockRefObj.Copy
 nieuwelement.Move pb1, pe2
 If OptionButton1.Value = True Then qw = qw - 1
 If OptionButton2.Value = True Then qw = qw + 1
 Next I
 ' MEESTE RECHTSE BLOK
 If OptionButton1.Value = True Then varAttributes(0).textstring = groepinvoerBox1  'OPTIONBUTTON1.Value = True
 If OptionButton2.Value = True Then varAttributes(0).textstring = "1" 'CheckBox4.Value = True
 nieuwelement.Update
 
 D = (a * 44.6)
 Dim LijnObj As AcadPolyline
' Dim Lijnobj As Object
 Dim pb2(0 To 2) As Double 'punt van rechthoek
 Dim pb3(0 To 2) As Double 'punt van rechthoek
 Dim pb4(0 To 2) As Double 'punt van rechthoek
 Dim pb5(0 To 2) As Double 'punt voor regelunittekst
 
 pb1(0) = pb1(0) - 3    'montage blok op zelfde hoogte als insertionpoint
 pb1(1) = pb1(1) + 3    'montage blok op zelfde hoogte als insertionpoint
 pb1(2) = pb1(2)        'montage blok op zelfde hoogte als insertionpoint
 
 
 pb3(0) = pb1(0) - ((D + 100) * scaal)
 pb3(1) = pb1(1) + (250 * scaal)
 pb3(2) = 0
 
 pb2(0) = pb1(0)
 pb2(1) = pb3(1)
 pb2(2) = 0
 
 pb4(0) = pb3(0)
 pb4(1) = pb1(1)
 pb4(2) = 0
 
 pb5(0) = pb3(0)
 pb5(1) = pb3(1) + (13 * scaal)
 pb5(2) = 0
 


   
Dim points(0 To 14) As Double
points(0) = pb1(0): points(1) = pb1(1): points(2) = pb1(2)
points(3) = pb2(0): points(4) = pb2(1): points(5) = pb2(2)
points(6) = pb3(0): points(7) = pb3(1): points(8) = pb3(2)
points(9) = pb4(0): points(10) = pb4(1): points(11) = pb4(2)
points(12) = pb1(0): points(13) = pb1(1): points(14) = pb1(2)

 Set LijnObj = ThisDrawing.ModelSpace.AddPolyline(points)
 LijnObj.Offset (3)
 LijnObj.Update
 
 If MontageblokForm.CheckBox3.Value = False Then
 z = Val(groepinvoerBox2.Value)
 If z > 0 And z < 10 Then z = "0" & groepinvoerBox2.Value
 End If
 If MontageblokForm.CheckBox3.Value = True Then
    z = groepinvoerBox2.Value
 End If
 
 Dim e As Double
 e = groepinvoerBox2.Text
 f = "Regelunit" & " " & z
 
 Dim textobj As AcadText
 Set textobj = ThisDrawing.ModelSpace.AddText(f, pb5, (15 * scaal))
 textobj.Update
 
 Dim pb6(0 To 2) As Double
   
 e = (D \ 2)
 pb6(0) = pb3(0) + ((e + 48) * scaal)
 pb6(1) = pb3(1) - (30 * scaal)
 pb6(2) = 0
 
 'Dim textObj As AcadText
 Set textobj = ThisDrawing.ModelSpace.AddText("AANSLUITSCHEMA", pb6, (14 * scaal))
 textobj.Alignment = acAlignmentMiddleCenter
 textobj.TextAlignmentPoint = pb6
 textobj.Update
   
 pb6(0) = pb6(0)
 pb6(1) = pb6(1) - (25 * scaal)
 pb6(2) = 0
 
 Set textobj = ThisDrawing.ModelSpace.AddText("MONTEURS WTH", pb6, (14 * scaal))
 textobj.Alignment = acAlignmentMiddleCenter
 textobj.TextAlignmentPoint = pb6
 textobj.Update
 
 Call zoekblok2
 groepinvoerBox1.Value = Clear 'aantal groepen invoerveld
   If CheckBox6.Enabled = True Then
        groepinvoerBox2 = groepinvoerBox2 + 1
        Else
        groepinvoerBox2.Value = Clear 'regelunit invoerveld
   End If
 groepinvoerBox2.SetFocus
 Label2.Caption = Clear
 ThisDrawing.ObjectSnapMode = False
 MontageblokForm.Show
If CheckBox6.Enabled = True Then
    MontageblokForm.Hide
    Call zoekblok1
End If
End Sub

Private Sub resetButton_Click()
Call zoekblok2
 groepinvoerBox1.Value = Clear 'aantal groepen invoerveld
 groepinvoerBox2.Value = Clear 'regelunit invoerveld
 groepinvoerBox2.SetFocus
 Label2.Caption = Clear
 TextBox1 = ""
 OptionButton1.Value = False
 OptionButton2.Value = False
 CheckBox5.Value = False
End Sub
Sub Schaal(scaal)
MontageblokForm.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
Update
End Sub

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
Sub combolijst1()

blokken.ComboBox1.AddItem "Badkamer"
blokken.ComboBox1.AddItem "Bedrijfsruimte1"
blokken.ComboBox1.AddItem "Bedrijfsruimte2"
blokken.ComboBox1.AddItem "Berging"
blokken.ComboBox1.AddItem "Bijkeuken"
blokken.ComboBox1.AddItem "Bureel"
blokken.ComboBox1.AddItem "Directiekamer"
blokken.ComboBox1.AddItem "Douche"
blokken.ComboBox1.AddItem "Eetkamer"
blokken.ComboBox1.AddItem "Entree"
blokken.ComboBox1.AddItem "Gang"
blokken.ComboBox1.AddItem "Garage"
blokken.ComboBox1.AddItem "Groepsruimte"
blokken.ComboBox1.AddItem "Groepsruimte1"
blokken.ComboBox1.AddItem "Groepsruimte2"
blokken.ComboBox1.AddItem "Hal"
blokken.ComboBox1.AddItem "Hobby"
blokken.ComboBox1.AddItem "Kantine"
blokken.ComboBox1.AddItem "Kantoor"
blokken.ComboBox1.AddItem "Kantoor1"
blokken.ComboBox1.AddItem "Kantoor2"
blokken.ComboBox1.AddItem "Keuken"
blokken.ComboBox1.AddItem "Opkamer"
blokken.ComboBox1.AddItem "Opslag"
blokken.ComboBox1.AddItem "Overloop"
blokken.ComboBox1.AddItem "Portaal"
blokken.ComboBox1.AddItem "Serre"
blokken.ComboBox1.AddItem "Slaapkamer"
blokken.ComboBox1.AddItem "Slaapkamer1"
blokken.ComboBox1.AddItem "Slaapkamer2"
blokken.ComboBox1.AddItem "Slaapkamer3"
blokken.ComboBox1.AddItem "Slaapkamer4"
blokken.ComboBox1.AddItem "Spoelkeuken"
blokken.ComboBox1.AddItem "Studeerkamer"
blokken.ComboBox1.AddItem "Toilet"
blokken.ComboBox1.AddItem "Tuinkamer"
blokken.ComboBox1.AddItem "Verblijfsruimte"
blokken.ComboBox1.AddItem "Verblijfsruimte1"
blokken.ComboBox1.AddItem "Verblijfsruimte2"
blokken.ComboBox1.AddItem "Verkoop"
blokken.ComboBox1.AddItem "Voorkamer"
blokken.ComboBox1.AddItem "W.C"
blokken.ComboBox1.AddItem "Werkkamer"
blokken.ComboBox1.AddItem "Winkel"
blokken.ComboBox1.AddItem "Woonkamer"
blokken.ComboBox1.AddItem "Zitkamer"
blokken.ComboBox1.AddItem "Zolder"
blokken.ComboBox1.AddItem "Zwembad"
blokken.ComboBox1.MatchEntry = fmMatchEntryFirstLetter
End Sub

Sub Combolijst2()

blokken.ComboBox2.AddItem "Badkamer"
blokken.ComboBox2.AddItem "Bedrijfsruimte1"
blokken.ComboBox2.AddItem "Bedrijfsruimte2"
blokken.ComboBox2.AddItem "Berging"
blokken.ComboBox2.AddItem "Bijkeuken"
blokken.ComboBox2.AddItem "Bureel"
blokken.ComboBox2.AddItem "Directiekamer"
blokken.ComboBox2.AddItem "Douche"
blokken.ComboBox2.AddItem "Eetkamer"
blokken.ComboBox2.AddItem "Entree"
blokken.ComboBox2.AddItem "Gang"
blokken.ComboBox2.AddItem "Garage"
blokken.ComboBox2.AddItem "Groepsruimte"
blokken.ComboBox2.AddItem "Groepsruimte1"
blokken.ComboBox2.AddItem "Groepsruimte2"
blokken.ComboBox2.AddItem "Hal"
blokken.ComboBox2.AddItem "Hobby"
blokken.ComboBox2.AddItem "Kantine"
blokken.ComboBox2.AddItem "Kantoor"
blokken.ComboBox2.AddItem "Kantoor1"
blokken.ComboBox2.AddItem "Kantoor2"
blokken.ComboBox2.AddItem "Keuken"
blokken.ComboBox2.AddItem "Opkamer"
blokken.ComboBox2.AddItem "Opslag"
blokken.ComboBox2.AddItem "Overloop"
blokken.ComboBox2.AddItem "Portaal"
blokken.ComboBox2.AddItem "Serre"
blokken.ComboBox2.AddItem "Slaapkamer"
blokken.ComboBox2.AddItem "Slaapkamer1"
blokken.ComboBox2.AddItem "Slaapkamer2"
blokken.ComboBox2.AddItem "Slaapkamer3"
blokken.ComboBox2.AddItem "Slaapkamer4"
blokken.ComboBox2.AddItem "Spoelkeuken"
blokken.ComboBox2.AddItem "Studeerkamer"
blokken.ComboBox2.AddItem "Toilet"
blokken.ComboBox2.AddItem "Tuinkamer"
blokken.ComboBox2.AddItem "Verblijfsruimte"
blokken.ComboBox2.AddItem "Verblijfsruimte1"
blokken.ComboBox2.AddItem "Verblijfsruimte2"
blokken.ComboBox2.AddItem "Verkoop"
blokken.ComboBox2.AddItem "Voorkamer"
blokken.ComboBox2.AddItem "W.C"
blokken.ComboBox2.AddItem "Werkkamer"
blokken.ComboBox2.AddItem "Winkel"
blokken.ComboBox2.AddItem "Woonkamer"
blokken.ComboBox2.AddItem "Zitkamer"
blokken.ComboBox2.AddItem "Zolder"
blokken.ComboBox2.AddItem "Zwembad"
blokken.ComboBox2.MatchEntry = fmMatchEntryFirstLetter
End Sub

Sub Combolijst3()

blokken.ComboBox3.AddItem "Badkamer"
blokken.ComboBox3.AddItem "Bedrijfsruimte1"
blokken.ComboBox3.AddItem "Bedrijfsruimte2"
blokken.ComboBox3.AddItem "Berging"
blokken.ComboBox3.AddItem "Bijkeuken"
blokken.ComboBox3.AddItem "Bureel"
blokken.ComboBox3.AddItem "Directiekamer"
blokken.ComboBox3.AddItem "Douche"
blokken.ComboBox3.AddItem "Eetkamer"
blokken.ComboBox3.AddItem "Entree"
blokken.ComboBox3.AddItem "Gang"
blokken.ComboBox3.AddItem "Garage"
blokken.ComboBox3.AddItem "Groepsruimte"
blokken.ComboBox3.AddItem "Groepsruimte1"
blokken.ComboBox3.AddItem "Groepsruimte2"
blokken.ComboBox3.AddItem "Hal"
blokken.ComboBox3.AddItem "Hobby"
blokken.ComboBox3.AddItem "Kantine"
blokken.ComboBox3.AddItem "Kantoor"
blokken.ComboBox3.AddItem "Kantoor1"
blokken.ComboBox3.AddItem "Kantoor2"
blokken.ComboBox3.AddItem "Keuken"
blokken.ComboBox3.AddItem "Opkamer"
blokken.ComboBox3.AddItem "Opslag"
blokken.ComboBox3.AddItem "Overloop"
blokken.ComboBox3.AddItem "Portaal"
blokken.ComboBox3.AddItem "Serre"
blokken.ComboBox3.AddItem "Slaapkamer"
blokken.ComboBox3.AddItem "Slaapkamer1"
blokken.ComboBox3.AddItem "Slaapkamer2"
blokken.ComboBox3.AddItem "Slaapkamer3"
blokken.ComboBox3.AddItem "Slaapkamer4"
blokken.ComboBox3.AddItem "Spoelkeuken"
blokken.ComboBox3.AddItem "Studeerkamer"
blokken.ComboBox3.AddItem "Toilet"
blokken.ComboBox3.AddItem "Tuinkamer"
blokken.ComboBox3.AddItem "Verblijfsruimte"
blokken.ComboBox3.AddItem "Verblijfsruimte1"
blokken.ComboBox3.AddItem "Verblijfsruimte2"
blokken.ComboBox3.AddItem "Verkoop"
blokken.ComboBox3.AddItem "Voorkamer"
blokken.ComboBox3.AddItem "W.C"
blokken.ComboBox3.AddItem "Werkkamer"
blokken.ComboBox3.AddItem "Winkel"
blokken.ComboBox3.AddItem "Woonkamer"
blokken.ComboBox3.AddItem "Zitkamer"
blokken.ComboBox3.AddItem "Zolder"
blokken.ComboBox3.AddItem "Zwembad"
blokken.ComboBox3.MatchEntry = fmMatchEntryFirstLetter
End Sub

Sub combolijst4()

blokken.ComboBox4.AddItem "Badkamer"
blokken.ComboBox4.AddItem "Bedrijfsruimte1"
blokken.ComboBox4.AddItem "Bedrijfsruimte2"
blokken.ComboBox4.AddItem "Berging"
blokken.ComboBox4.AddItem "Bijkeuken"
blokken.ComboBox4.AddItem "Bureel"
blokken.ComboBox4.AddItem "Directiekamer"
blokken.ComboBox4.AddItem "Douche"
blokken.ComboBox4.AddItem "Eetkamer"
blokken.ComboBox4.AddItem "Entree"
blokken.ComboBox4.AddItem "Gang"
blokken.ComboBox4.AddItem "Garage"
blokken.ComboBox4.AddItem "Groepsruimte"
blokken.ComboBox4.AddItem "Groepsruimte1"
blokken.ComboBox4.AddItem "Groepsruimte2"
blokken.ComboBox4.AddItem "Hal"
blokken.ComboBox4.AddItem "Hobby"
blokken.ComboBox4.AddItem "Kantine"
blokken.ComboBox4.AddItem "Kantoor"
blokken.ComboBox4.AddItem "Kantoor1"
blokken.ComboBox4.AddItem "Kantoor2"
blokken.ComboBox4.AddItem "Keuken"
blokken.ComboBox4.AddItem "Opkamer"
blokken.ComboBox4.AddItem "Opslag"
blokken.ComboBox4.AddItem "Overloop"
blokken.ComboBox4.AddItem "Portaal"
blokken.ComboBox4.AddItem "Serre"
blokken.ComboBox4.AddItem "Slaapkamer"
blokken.ComboBox4.AddItem "Slaapkamer1"
blokken.ComboBox4.AddItem "Slaapkamer2"
blokken.ComboBox4.AddItem "Slaapkamer3"
blokken.ComboBox4.AddItem "Slaapkamer4"
blokken.ComboBox4.AddItem "Spoelkeuken"
blokken.ComboBox4.AddItem "Studeerkamer"
blokken.ComboBox4.AddItem "Toilet"
blokken.ComboBox4.AddItem "Tuinkamer"
blokken.ComboBox4.AddItem "Verblijfsruimte"
blokken.ComboBox4.AddItem "Verblijfsruimte1"
blokken.ComboBox4.AddItem "Verblijfsruimte2"
blokken.ComboBox4.AddItem "Verkoop"
blokken.ComboBox4.AddItem "Voorkamer"
blokken.ComboBox4.AddItem "W.C"
blokken.ComboBox4.AddItem "Werkkamer"
blokken.ComboBox4.AddItem "Winkel"
blokken.ComboBox4.AddItem "Woonkamer"
blokken.ComboBox4.AddItem "Zitkamer"
blokken.ComboBox4.AddItem "Zolder"
blokken.ComboBox4.AddItem "Zwembad"
blokken.ComboBox4.MatchEntry = fmMatchEntryFirstLetter
End Sub

Sub Combolijst5()

blokken.ComboBox5.AddItem "Badkamer"
blokken.ComboBox5.AddItem "Bedrijfsruimte1"
blokken.ComboBox5.AddItem "Bedrijfsruimte2"
blokken.ComboBox5.AddItem "Berging"
blokken.ComboBox5.AddItem "Bijkeuken"
blokken.ComboBox5.AddItem "Bureel"
blokken.ComboBox5.AddItem "Directiekamer"
blokken.ComboBox5.AddItem "Douche"
blokken.ComboBox5.AddItem "Eetkamer"
blokken.ComboBox5.AddItem "Entree"
blokken.ComboBox5.AddItem "Gang"
blokken.ComboBox5.AddItem "Garage"
blokken.ComboBox5.AddItem "Groepsruimte"
blokken.ComboBox5.AddItem "Groepsruimte1"
blokken.ComboBox5.AddItem "Groepsruimte2"
blokken.ComboBox5.AddItem "Hal"
blokken.ComboBox5.AddItem "Hobby"
blokken.ComboBox5.AddItem "Kantine"
blokken.ComboBox5.AddItem "Kantoor"
blokken.ComboBox5.AddItem "Kantoor1"
blokken.ComboBox5.AddItem "Kantoor2"
blokken.ComboBox5.AddItem "Keuken"
blokken.ComboBox5.AddItem "Opkamer"
blokken.ComboBox5.AddItem "Opslag"
blokken.ComboBox5.AddItem "Overloop"
blokken.ComboBox5.AddItem "Portaal"
blokken.ComboBox5.AddItem "Serre"
blokken.ComboBox5.AddItem "Slaapkamer"
blokken.ComboBox5.AddItem "Slaapkamer1"
blokken.ComboBox5.AddItem "Slaapkamer2"
blokken.ComboBox5.AddItem "Slaapkamer3"
blokken.ComboBox5.AddItem "Slaapkamer4"
blokken.ComboBox5.AddItem "Spoelkeuken"
blokken.ComboBox5.AddItem "Studeerkamer"
blokken.ComboBox5.AddItem "Toilet"
blokken.ComboBox5.AddItem "Tuinkamer"
blokken.ComboBox5.AddItem "Verblijfsruimte"
blokken.ComboBox5.AddItem "Verblijfsruimte1"
blokken.ComboBox5.AddItem "Verblijfsruimte2"
blokken.ComboBox5.AddItem "Verkoop"
blokken.ComboBox5.AddItem "Voorkamer"
blokken.ComboBox5.AddItem "W.C"
blokken.ComboBox5.AddItem "Werkkamer"
blokken.ComboBox5.AddItem "Winkel"
blokken.ComboBox5.AddItem "Woonkamer"
blokken.ComboBox5.AddItem "Zitkamer"
blokken.ComboBox5.AddItem "Zolder"
blokken.ComboBox5.AddItem "Zwembad"
blokken.ComboBox5.MatchEntry = fmMatchEntryFirstLetter
End Sub

Sub Combolijst6()

blokken.ComboBox6.AddItem "Badkamer"
blokken.ComboBox6.AddItem "Bedrijfsruimte1"
blokken.ComboBox6.AddItem "Bedrijfsruimte2"
blokken.ComboBox6.AddItem "Berging"
blokken.ComboBox6.AddItem "Bijkeuken"
blokken.ComboBox6.AddItem "Bureel"
blokken.ComboBox6.AddItem "Directiekamer"
blokken.ComboBox6.AddItem "Douche"
blokken.ComboBox6.AddItem "Eetkamer"
blokken.ComboBox6.AddItem "Entree"
blokken.ComboBox6.AddItem "Gang"
blokken.ComboBox6.AddItem "Garage"
blokken.ComboBox6.AddItem "Groepsruimte"
blokken.ComboBox6.AddItem "Groepsruimte1"
blokken.ComboBox6.AddItem "Groepsruimte2"
blokken.ComboBox6.AddItem "Hal"
blokken.ComboBox6.AddItem "Hobby"
blokken.ComboBox6.AddItem "Kantine"
blokken.ComboBox6.AddItem "Kantoor"
blokken.ComboBox6.AddItem "Kantoor1"
blokken.ComboBox6.AddItem "Kantoor2"
blokken.ComboBox6.AddItem "Keuken"
blokken.ComboBox6.AddItem "Opkamer"
blokken.ComboBox6.AddItem "Opslag"
blokken.ComboBox6.AddItem "Overloop"
blokken.ComboBox6.AddItem "Portaal"
blokken.ComboBox6.AddItem "Serre"
blokken.ComboBox6.AddItem "Slaapkamer"
blokken.ComboBox6.AddItem "Slaapkamer1"
blokken.ComboBox6.AddItem "Slaapkamer2"
blokken.ComboBox6.AddItem "Slaapkamer3"
blokken.ComboBox6.AddItem "Slaapkamer4"
blokken.ComboBox6.AddItem "Spoelkeuken"
blokken.ComboBox6.AddItem "Studeerkamer"
blokken.ComboBox6.AddItem "Toilet"
blokken.ComboBox6.AddItem "Tuinkamer"
blokken.ComboBox6.AddItem "Verblijfsruimte"
blokken.ComboBox6.AddItem "Verblijfsruimte1"
blokken.ComboBox6.AddItem "Verblijfsruimte2"
blokken.ComboBox6.AddItem "Verkoop"
blokken.ComboBox6.AddItem "Voorkamer"
blokken.ComboBox6.AddItem "W.C"
blokken.ComboBox6.AddItem "Werkkamer"
blokken.ComboBox6.AddItem "Winkel"
blokken.ComboBox6.AddItem "Woonkamer"
blokken.ComboBox6.AddItem "Zitkamer"
blokken.ComboBox6.AddItem "Zolder"
blokken.ComboBox6.AddItem "Zwembad"
blokken.ComboBox6.MatchEntry = fmMatchEntryFirstLetter
End Sub

Sub Combolijst7()

blokken.ComboBox7.AddItem "Badkamer"
blokken.ComboBox7.AddItem "Bedrijfsruimte1"
blokken.ComboBox7.AddItem "Bedrijfsruimte2"
blokken.ComboBox7.AddItem "Berging"
blokken.ComboBox7.AddItem "Bijkeuken"
blokken.ComboBox7.AddItem "Bureel"
blokken.ComboBox7.AddItem "Directiekamer"
blokken.ComboBox7.AddItem "Douche"
blokken.ComboBox7.AddItem "Eetkamer"
blokken.ComboBox7.AddItem "Entree"
blokken.ComboBox7.AddItem "Gang"
blokken.ComboBox7.AddItem "Garage"
blokken.ComboBox7.AddItem "Groepsruimte"
blokken.ComboBox7.AddItem "Groepsruimte1"
blokken.ComboBox7.AddItem "Groepsruimte2"
blokken.ComboBox7.AddItem "Hal"
blokken.ComboBox7.AddItem "Hobby"
blokken.ComboBox7.AddItem "Kantine"
blokken.ComboBox7.AddItem "Kantoor"
blokken.ComboBox7.AddItem "Kantoor1"
blokken.ComboBox7.AddItem "Kantoor2"
blokken.ComboBox7.AddItem "Keuken"
blokken.ComboBox7.AddItem "Opkamer"
blokken.ComboBox7.AddItem "Opslag"
blokken.ComboBox7.AddItem "Overloop"
blokken.ComboBox7.AddItem "Portaal"
blokken.ComboBox7.AddItem "Serre"
blokken.ComboBox7.AddItem "Slaapkamer"
blokken.ComboBox7.AddItem "Slaapkamer1"
blokken.ComboBox7.AddItem "Slaapkamer2"
blokken.ComboBox7.AddItem "Slaapkamer3"
blokken.ComboBox7.AddItem "Slaapkamer4"
blokken.ComboBox7.AddItem "Spoelkeuken"
blokken.ComboBox7.AddItem "Studeerkamer"
blokken.ComboBox7.AddItem "Toilet"
blokken.ComboBox7.AddItem "Tuinkamer"
blokken.ComboBox7.AddItem "Verblijfsruimte"
blokken.ComboBox7.AddItem "Verblijfsruimte1"
blokken.ComboBox7.AddItem "Verblijfsruimte2"
blokken.ComboBox7.AddItem "Verkoop"
blokken.ComboBox7.AddItem "Voorkamer"
blokken.ComboBox7.AddItem "W.C"
blokken.ComboBox7.AddItem "Werkkamer"
blokken.ComboBox7.AddItem "Winkel"
blokken.ComboBox7.AddItem "Woonkamer"
blokken.ComboBox7.AddItem "Zitkamer"
blokken.ComboBox7.AddItem "Zolder"
blokken.ComboBox7.AddItem "Zwembad"
blokken.ComboBox7.MatchEntry = fmMatchEntryFirstLetter
End Sub

Sub Combolijst8()

blokken.ComboBox8.AddItem "Badkamer"
blokken.ComboBox8.AddItem "Bedrijfsruimte1"
blokken.ComboBox8.AddItem "Bedrijfsruimte2"
blokken.ComboBox8.AddItem "Berging"
blokken.ComboBox8.AddItem "Bijkeuken"
blokken.ComboBox8.AddItem "Bureel"
blokken.ComboBox8.AddItem "Directiekamer"
blokken.ComboBox8.AddItem "Douche"
blokken.ComboBox8.AddItem "Eetkamer"
blokken.ComboBox8.AddItem "Entree"
blokken.ComboBox8.AddItem "Gang"
blokken.ComboBox8.AddItem "Garage"
blokken.ComboBox8.AddItem "Groepsruimte"
blokken.ComboBox8.AddItem "Groepsruimte1"
blokken.ComboBox8.AddItem "Groepsruimte2"
blokken.ComboBox8.AddItem "Hal"
blokken.ComboBox8.AddItem "Hobby"
blokken.ComboBox8.AddItem "Kantine"
blokken.ComboBox8.AddItem "Kantoor"
blokken.ComboBox8.AddItem "Kantoor1"
blokken.ComboBox8.AddItem "Kantoor2"
blokken.ComboBox8.AddItem "Keuken"
blokken.ComboBox8.AddItem "Opkamer"
blokken.ComboBox8.AddItem "Opslag"
blokken.ComboBox8.AddItem "Overloop"
blokken.ComboBox8.AddItem "Portaal"
blokken.ComboBox8.AddItem "Serre"
blokken.ComboBox8.AddItem "Slaapkamer"
blokken.ComboBox8.AddItem "Slaapkamer1"
blokken.ComboBox8.AddItem "Slaapkamer2"
blokken.ComboBox8.AddItem "Slaapkamer3"
blokken.ComboBox8.AddItem "Slaapkamer4"
blokken.ComboBox8.AddItem "Spoelkeuken"
blokken.ComboBox8.AddItem "Studeerkamer"
blokken.ComboBox8.AddItem "Toilet"
blokken.ComboBox8.AddItem "Tuinkamer"
blokken.ComboBox8.AddItem "Verblijfsruimte"
blokken.ComboBox8.AddItem "Verblijfsruimte1"
blokken.ComboBox8.AddItem "Verblijfsruimte2"
blokken.ComboBox8.AddItem "Verkoop"
blokken.ComboBox8.AddItem "Voorkamer"
blokken.ComboBox8.AddItem "W.C"
blokken.ComboBox8.AddItem "Werkkamer"
blokken.ComboBox8.AddItem "Winkel"
blokken.ComboBox8.AddItem "Woonkamer"
blokken.ComboBox8.AddItem "Zitkamer"
blokken.ComboBox8.AddItem "Zolder"
blokken.ComboBox8.AddItem "Zwembad"
blokken.ComboBox8.MatchEntry = fmMatchEntryFirstLetter
End Sub

Sub Combolijst9()

blokken.ComboBox9.AddItem "Badkamer"
blokken.ComboBox9.AddItem "Bedrijfsruimte1"
blokken.ComboBox9.AddItem "Bedrijfsruimte2"
blokken.ComboBox9.AddItem "Berging"
blokken.ComboBox9.AddItem "Bijkeuken"
blokken.ComboBox9.AddItem "Bureel"
blokken.ComboBox9.AddItem "Directiekamer"
blokken.ComboBox9.AddItem "Douche"
blokken.ComboBox9.AddItem "Eetkamer"
blokken.ComboBox9.AddItem "Entree"
blokken.ComboBox9.AddItem "Gang"
blokken.ComboBox9.AddItem "Garage"
blokken.ComboBox9.AddItem "Groepsruimte"
blokken.ComboBox9.AddItem "Groepsruimte1"
blokken.ComboBox9.AddItem "Groepsruimte2"
blokken.ComboBox9.AddItem "Hal"
blokken.ComboBox9.AddItem "Hobby"
blokken.ComboBox9.AddItem "Kantine"
blokken.ComboBox9.AddItem "Kantoor"
blokken.ComboBox9.AddItem "Kantoor1"
blokken.ComboBox9.AddItem "Kantoor2"
blokken.ComboBox9.AddItem "Keuken"
blokken.ComboBox9.AddItem "Opkamer"
blokken.ComboBox9.AddItem "Opslag"
blokken.ComboBox9.AddItem "Overloop"
blokken.ComboBox9.AddItem "Portaal"
blokken.ComboBox9.AddItem "Serre"
blokken.ComboBox9.AddItem "Slaapkamer"
blokken.ComboBox9.AddItem "Slaapkamer1"
blokken.ComboBox9.AddItem "Slaapkamer2"
blokken.ComboBox9.AddItem "Slaapkamer3"
blokken.ComboBox9.AddItem "Slaapkamer4"
blokken.ComboBox9.AddItem "Spoelkeuken"
blokken.ComboBox9.AddItem "Studeerkamer"
blokken.ComboBox9.AddItem "Toilet"
blokken.ComboBox9.AddItem "Tuinkamer"
blokken.ComboBox9.AddItem "Verblijfsruimte"
blokken.ComboBox9.AddItem "Verblijfsruimte1"
blokken.ComboBox9.AddItem "Verblijfsruimte2"
blokken.ComboBox9.AddItem "Verkoop"
blokken.ComboBox9.AddItem "Voorkamer"
blokken.ComboBox9.AddItem "W.C"
blokken.ComboBox9.AddItem "Werkkamer"
blokken.ComboBox9.AddItem "Winkel"
blokken.ComboBox9.AddItem "Woonkamer"
blokken.ComboBox9.AddItem "Zitkamer"
blokken.ComboBox9.AddItem "Zolder"
blokken.ComboBox9.AddItem "Zwembad"
blokken.ComboBox9.MatchEntry = fmMatchEntryFirstLetter
End Sub
Sub imagelijst1()
    MontageblokForm.Image1.Visible = False
    MontageblokForm.Image2.Visible = False
    MontageblokForm.Image3.Visible = False
    MontageblokForm.Image4.Visible = False
    MontageblokForm.Image5.Visible = False
    MontageblokForm.Image6.Visible = False
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
    groepinvoerBox1.SetFocus
    PlaatsButton.Enabled = False
End Sub
Sub imagelijst2()
    MontageblokForm.Image1.Visible = True
    MontageblokForm.Image2.Visible = False
    MontageblokForm.Image3.Visible = False
    MontageblokForm.Image4.Visible = False
    MontageblokForm.Image5.Visible = False
    MontageblokForm.Image6.Visible = False
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst3()
    MontageblokForm.Image1.Visible = True
    MontageblokForm.Image2.Visible = True
    MontageblokForm.Image3.Visible = False
    MontageblokForm.Image4.Visible = False
    MontageblokForm.Image5.Visible = False
    MontageblokForm.Image6.Visible = False
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst4()
    MontageblokForm.Image1.Visible = True
    MontageblokForm.Image2.Visible = True
    MontageblokForm.Image3.Visible = True
    MontageblokForm.Image4.Visible = False
    MontageblokForm.Image5.Visible = False
    MontageblokForm.Image6.Visible = False
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst5()
    MontageblokForm.Image1.Visible = True
    MontageblokForm.Image2.Visible = True
    MontageblokForm.Image3.Visible = True
    MontageblokForm.Image4.Visible = True
    MontageblokForm.Image5.Visible = False
    MontageblokForm.Image6.Visible = False
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst6()
    MontageblokForm.Image1.Visible = True
    MontageblokForm.Image2.Visible = True
    MontageblokForm.Image3.Visible = True
    MontageblokForm.Image4.Visible = True
    MontageblokForm.Image5.Visible = True
    MontageblokForm.Image6.Visible = False
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst7()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = False
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst8()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = False
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst9()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = False
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst10()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = False
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst11()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = False
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst12()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = False
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst13()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = False
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst14()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = False
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst15()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = False
    MontageblokForm.Image16.Visible = False
    MontageblokForm.Image17.Visible = False
    MontageblokForm.Image18.Visible = False
    MontageblokForm.Image19.Visible = False
    MontageblokForm.Image20.Visible = False
End Sub
Sub imagelijst16()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = True
    MontageblokForm.Image16.Visible = False
    MontageblokForm.Image17.Visible = False
    MontageblokForm.Image18.Visible = False
    MontageblokForm.Image19.Visible = False
    MontageblokForm.Image20.Visible = False
End Sub
Sub imagelijst17()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = True
    MontageblokForm.Image16.Visible = True
    MontageblokForm.Image17.Visible = False
    MontageblokForm.Image18.Visible = False
    MontageblokForm.Image19.Visible = False
    MontageblokForm.Image20.Visible = False
End Sub
Sub imagelijst18()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = True
    MontageblokForm.Image16.Visible = True
    MontageblokForm.Image17.Visible = True
    MontageblokForm.Image18.Visible = False
    MontageblokForm.Image19.Visible = False
    MontageblokForm.Image20.Visible = False
End Sub
Sub imagelijst19()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = True
    MontageblokForm.Image16.Visible = True
    MontageblokForm.Image17.Visible = True
    MontageblokForm.Image18.Visible = True
    MontageblokForm.Image19.Visible = False
    MontageblokForm.Image20.Visible = False
End Sub
Sub imagelijst20()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = True
    MontageblokForm.Image16.Visible = True
    MontageblokForm.Image17.Visible = True
    MontageblokForm.Image18.Visible = True
    MontageblokForm.Image19.Visible = True
    MontageblokForm.Image20.Visible = False
End Sub
Sub imagelijst21()
    MontageblokForm.Image1.Visible = True
    MontageblokForm.Image2.Visible = True
    MontageblokForm.Image3.Visible = True
    MontageblokForm.Image4.Visible = True
    MontageblokForm.Image5.Visible = True
    MontageblokForm.Image6.Visible = True
    MontageblokForm.Image7.Visible = True
    MontageblokForm.Image8.Visible = True
    MontageblokForm.Image9.Visible = True
    MontageblokForm.Image10.Visible = True
    MontageblokForm.Image11.Visible = True
    MontageblokForm.Image12.Visible = True
    MontageblokForm.Image13.Visible = True
    MontageblokForm.Image14.Visible = True
    MontageblokForm.Image15.Visible = True
    MontageblokForm.Image16.Visible = True
    MontageblokForm.Image17.Visible = True
    MontageblokForm.Image18.Visible = True
    MontageblokForm.Image19.Visible = True
    MontageblokForm.Image20.Visible = True
End Sub

Attribute VB_Name = "blokken"
Attribute VB_Base = "0{FA0740AD-998A-439B-8244-0BB030D2D3AA}{E21773B1-34A1-4FBF-9C8D-E9941A585D4E}"
Attribute VB_GlobalNameSpace = False
Attribute VB_Creatable = False
Attribute VB_PredeclaredId = True
Attribute VB_Exposed = False
Attribute VB_TemplateDerived = False
Attribute VB_Customizable = False
'14-08-2002 M.Bosch & G.C.Haak
'bijbehorende blokken:
'bltekor.dwg (1 radiator)
'bltekor1.dwg (2-3 radiator)
'bltekor2.dwg (4-6 radiator)
'bltekor3.dwg (7-9 radiator)
Dim nummer As Integer
Dim pbegin
Dim myValue As Integer

'Option Explicit

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000

Private Sub CommandButton2_Click()
blokken.Hide
Dim bestand As String
bestand = "C:\acad2002\dwg\Bl-hr.dwg"
Dim pb1 As Variant
pb1 = ThisDrawing.Utility.GetPoint(, "Plaats startpunt....")
Set blockRefObj = ThisDrawing.ModelSpace.InsertBlock(pb1, bestand, 1, 1, 1, 0)
Unload Me
End Sub


Private Sub UserForm_Initialize()

'begin sluiten toets uitschakelen
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
'einde sluiten toets uitschakelen

For I = 0 To MultiPage2.Count - 1 'met de 1e page laten beginnen
MultiPage2.Value = I - 1
Next I

nummer = 0

Call ThisDrawing.combolijst1
Call ThisDrawing.Combolijst2
Call ThisDrawing.Combolijst3
Call ThisDrawing.combolijst4
Call ThisDrawing.Combolijst5
Call ThisDrawing.Combolijst6
Call ThisDrawing.Combolijst7
Call ThisDrawing.Combolijst8
Call ThisDrawing.Combolijst9

Dim lognaam
lognaam = ThisDrawing.GetVariable("loginname")
lognaam = UCase(lognaam)

If lognaam = "GERARD" Then blokken.StartUpPosition = 0

End Sub
Private Sub CheckBox1_Click()
If CheckBox1.Value = True Then
      nummer = nummer + 1
   Else
      nummer = nummer - 1
   End If
   If nummer > 0 Then
      CmdButton1.Enabled = True
   Else
      CmdButton1.Enabled = False
End If

If CheckBox1.Value = True Then
blokken.Hide
frmbouwtek.Show
End If
End Sub
Private Sub CheckBox2_Click()
If CheckBox2.Value = True Then
      nummer = nummer + 1
   Else
      nummer = nummer - 1
   End If
   If nummer > 0 Then
      CmdButton1.Enabled = True
   Else
      CmdButton1.Enabled = False
End If

If CheckBox2.Value = True Then
blokken.Hide
frmBouwnummer.Show
End If
End Sub

Private Sub TextBox1_Change()
Dim a As Double
On Error Resume Next
a = TextBox1.Text
If Err Then
   TextBox1 = Clear
  Exit Sub
  End If
End Sub
Private Sub TextBox2_Change()
Dim a As Double
On Error Resume Next
a = TextBox2.Text
If Err Then
   TextBox2 = Clear
  Exit Sub
  End If
End Sub
Private Sub TextBox3_Change()
Dim a As Double
On Error Resume Next
a = TextBox3.Text
If Err Then
   TextBox3 = Clear
  Exit Sub
  End If
End Sub
Private Sub TextBox4_Change()
Dim a As Double
On Error Resume Next
a = TextBox4.Text
If Err Then
   TextBox4 = Clear
  Exit Sub
  End If
End Sub
Private Sub TextBox5_Change()
Dim a As Double
On Error Resume Next
a = TextBox5.Text
If Err Then
   TextBox5 = Clear
  Exit Sub
  End If
End Sub
Private Sub TextBox6_Change()
Dim a As Double
On Error Resume Next
a = TextBox6.Text
If Err Then
   TextBox6 = Clear
  Exit Sub
  End If
End Sub
Private Sub TextBox7_Change()
Dim a As Double
On Error Resume Next
a = TextBox7.Text
If Err Then
   TextBox7 = Clear
  Exit Sub
  End If
End Sub
Private Sub TextBox8_Change()
Dim a As Double
On Error Resume Next
a = TextBox8.Text
If Err Then
   TextBox8 = Clear
  Exit Sub
  End If
End Sub
Private Sub TextBox9_Change()
Dim a As Double
On Error Resume Next
a = TextBox9.Text
If Err Then
   TextBox9 = Clear
  Exit Sub
  End If
End Sub
Private Sub TextBox10_Change()
Dim a As Double
On Error Resume Next
a = TextBox10.Text
If a > 0 Then TextBox10 = Clear
End Sub
Private Sub TextBox11_Change()
Dim a As Double
On Error Resume Next
a = TextBox11.Text
If a > 0 Then TextBox11 = Clear
End Sub
Private Sub TextBox12_Change()
Dim a As Double
On Error Resume Next
a = TextBox12.Text
If a > 0 Then TextBox12 = Clear
End Sub
Private Sub TextBox13_Change()
Dim a As Double
On Error Resume Next
a = TextBox13.Text
If a > 0 Then TextBox13 = Clear
End Sub
Private Sub TextBox14_Change()
Dim a As Double
On Error Resume Next
a = TextBox14.Text
If a > 0 Then TextBox14 = Clear
End Sub
Private Sub TextBox15_Change()
Dim a As Double
On Error Resume Next
a = TextBox15.Text
If a > 0 Then TextBox15 = Clear
End Sub
Private Sub TextBox16_Change()
Dim a As Double
On Error Resume Next
a = TextBox16.Text
If a > 0 Then TextBox16 = Clear
End Sub
Private Sub TextBox17_Change()
Dim a As Double
On Error Resume Next
a = TextBox17.Text
If a > 0 Then TextBox17 = Clear
End Sub
Private Sub TextBox18_Change()
Dim a As Double
On Error Resume Next
a = TextBox18.Text
If a > 0 Then TextBox18 = Clear
End Sub
Private Sub OptionButton1_Click()
OptionButton10.Enabled = True
If OptionButton1.Value = True And OptionButton10.Value = False Then
ComboBox1.Left = 210: Label2.Left = 210: CmdButton1.Enabled = True
TextBox1.Visible = True: TextBox2.Visible = False: TextBox3.Visible = False
TextBox4.Visible = False: TextBox5.Visible = False: TextBox6.Visible = False
TextBox7.Visible = False: TextBox8.Visible = False: TextBox9.Visible = False

TextBox10.Visible = True: TextBox11.Visible = False: TextBox12.Visible = False
TextBox13.Visible = False: TextBox14.Visible = False: TextBox15.Visible = False
TextBox16.Visible = False: TextBox17.Visible = False: TextBox18.Visible = False

ComboBox1.Visible = True: ComboBox2.Visible = False: ComboBox3.Visible = False
ComboBox4.Visible = False: ComboBox5.Visible = False: ComboBox6.Visible = False
ComboBox7.Visible = False: ComboBox8.Visible = False: ComboBox9.Visible = False

TextBox1.SetFocus: Label1.Visible = True: Label2.Visible = True
End If

If OptionButton1.Value = True And OptionButton10.Value = True Then
ComboBox1.Visible = True: ComboBox2.Visible = False: ComboBox3.Visible = False
ComboBox4.Visible = False: ComboBox5.Visible = False: ComboBox6.Visible = False
ComboBox7.Visible = False: ComboBox8.Visible = False: ComboBox9.Visible = False
OptionButton1.Caption = "RUIMTE 1"
End If
End Sub
Private Sub OptionButton2_Click()
OptionButton10.Enabled = True
If OptionButton2.Value = True And OptionButton10.Value = False Then
ComboBox2.Left = 210: Label2.Left = 210: CmdButton1.Enabled = True
TextBox1.Visible = True: TextBox2.Visible = True: TextBox3.Visible = False
TextBox4.Visible = False: TextBox5.Visible = False: TextBox6.Visible = False
TextBox7.Visible = False: TextBox8.Visible = False: TextBox9.Visible = False

TextBox10.Visible = True: TextBox11.Visible = True: TextBox12.Visible = False
TextBox13.Visible = False: TextBox14.Visible = False: TextBox15.Visible = False
TextBox16.Visible = False: TextBox17.Visible = False: TextBox18.Visible = False

ComboBox1.Visible = True: ComboBox2.Visible = True: ComboBox3.Visible = False
ComboBox4.Visible = False: ComboBox5.Visible = False: ComboBox6.Visible = False
ComboBox7.Visible = False: ComboBox8.Visible = False: ComboBox9.Visible = False

TextBox1.SetFocus: Label1.Visible = True: Label2.Visible = True
End If

If OptionButton2.Value = True And OptionButton10.Value = True Then
ComboBox1.Visible = True: ComboBox2.Visible = True: ComboBox3.Visible = False
ComboBox4.Visible = False: ComboBox5.Visible = False: ComboBox6.Visible = False
ComboBox7.Visible = False: ComboBox8.Visible = False: ComboBox9.Visible = False
OptionButton1.Caption = "RUIMTE 1": OptionButton2.Caption = "RUIMTE 2"
End If

End Sub
Private Sub OptionButton3_Click()
OptionButton10.Enabled = True
If OptionButton3.Value = True And OptionButton10.Value = False Then
ComboBox3.Left = 210: Label2.Left = 210: CmdButton1.Enabled = True
TextBox1.Visible = True: TextBox2.Visible = True: TextBox3.Visible = True
TextBox4.Visible = False: TextBox5.Visible = False: TextBox6.Visible = False
TextBox7.Visible = False: TextBox8.Visible = False: TextBox9.Visible = False

TextBox10.Visible = True: TextBox11.Visible = True: TextBox12.Visible = True
TextBox13.Visible = False: TextBox14.Visible = False: TextBox15.Visible = False
TextBox16.Visible = False: TextBox17.Visible = False: TextBox18.Visible = False

ComboBox1.Visible = True: ComboBox2.Visible = True: ComboBox3.Visible = True
ComboBox4.Visible = False: ComboBox5.Visible = False: ComboBox6.Visible = False
ComboBox7.Visible = False: ComboBox8.Visible = False: ComboBox9.Visible = False

TextBox1.SetFocus: Label1.Visible = True: Label2.Visible = True
End If

If OptionButton3.Value = True And OptionButton10.Value = True Then
ComboBox1.Visible = True: ComboBox2.Visible = True: ComboBox3.Visible = True
ComboBox4.Visible = False: ComboBox5.Visible = False: ComboBox6.Visible = False
ComboBox7.Visible = False: ComboBox8.Visible = False: ComboBox9.Visible = False
OptionButton1.Caption = "RUIMTE 1": OptionButton2.Caption = "RUIMTE 2"
OptionButton3.Caption = "RUIMTE 3"
End If
End Sub
Private Sub OptionButton4_Click()
OptionButton10.Enabled = True
If OptionButton4.Value = True And OptionButton10.Value = False Then
ComboBox4.Left = 210: Label2.Left = 210: CmdButton1.Enabled = True
TextBox1.Visible = True: TextBox2.Visible = True: TextBox3.Visible = True
TextBox4.Visible = True: TextBox5.Visible = False: TextBox6.Visible = False
TextBox7.Visible = False: TextBox8.Visible = False: TextBox9.Visible = False

TextBox10.Visible = True: TextBox11.Visible = True: TextBox12.Visible = True
TextBox13.Visible = True: TextBox14.Visible = False: TextBox15.Visible = False
TextBox16.Visible = False: TextBox17.Visible = False: TextBox18.Visible = False

ComboBox1.Visible = True: ComboBox2.Visible = True: ComboBox3.Visible = True
ComboBox4.Visible = True: ComboBox5.Visible = False: ComboBox6.Visible = False
ComboBox7.Visible = False: ComboBox8.Visible = False: ComboBox9.Visible = False

TextBox1.SetFocus: Label1.Visible = True: Label2.Visible = True
End If

If OptionButton4.Value = True And OptionButton10.Value = True Then
ComboBox1.Visible = True: ComboBox2.Visible = True: ComboBox3.Visible = True
ComboBox4.Visible = True: ComboBox5.Visible = False: ComboBox6.Visible = False
ComboBox7.Visible = False: ComboBox8.Visible = False: ComboBox9.Visible = False
OptionButton1.Caption = "RUIMTE 1": OptionButton2.Caption = "RUIMTE 2"
OptionButton3.Caption = "RUIMTE 3": OptionButton4.Caption = "RUIMTE 4"
End If
End Sub
Private Sub OptionButton5_Click()
OptionButton10.Enabled = True
If OptionButton5.Value = True And OptionButton10.Value = False Then
ComboBox5.Left = 210: Label2.Left = 210: CmdButton1.Enabled = True
TextBox1.Visible = True: TextBox2.Visible = True: TextBox3.Visible = True
TextBox4.Visible = True: TextBox5.Visible = True: TextBox6.Visible = False
TextBox7.Visible = False: TextBox8.Visible = False: TextBox9.Visible = False

TextBox10.Visible = True: TextBox11.Visible = True: TextBox12.Visible = True
TextBox13.Visible = True: TextBox14.Visible = True: TextBox15.Visible = False
TextBox16.Visible = False: TextBox17.Visible = False: TextBox18.Visible = False

ComboBox1.Visible = True: ComboBox2.Visible = True: ComboBox3.Visible = True
ComboBox4.Visible = True: ComboBox5.Visible = True: ComboBox6.Visible = False
ComboBox7.Visible = False: ComboBox8.Visible = False: ComboBox9.Visible = False

TextBox1.SetFocus: Label1.Visible = True: Label2.Visible = True
End If

If OptionButton5.Value = True And OptionButton10.Value = True Then
ComboBox1.Visible = True: ComboBox2.Visible = True: ComboBox3.Visible = True
ComboBox4.Visible = True: ComboBox5.Visible = True: ComboBox6.Visible = False
ComboBox7.Visible = False: ComboBox8.Visible = False: ComboBox9.Visible = False
OptionButton1.Caption = "RUIMTE 1": OptionButton2.Caption = "RUIMTE 2"
OptionButton3.Caption = "RUIMTE 3": OptionButton4.Caption = "RUIMTE 4"
OptionButton5.Caption = "RUIMTE 5"
End If

End Sub
Private Sub OptionButton6_Click()
OptionButton10.Enabled = True
If OptionButton6.Value = True And OptionButton10.Value = False Then
ComboBox6.Left = 210: Label2.Left = 210: CmdButton1.Enabled = True
TextBox1.Visible = True: TextBox2.Visible = True: TextBox3.Visible = True
TextBox4.Visible = True: TextBox5.Visible = True: TextBox6.Visible = True
TextBox7.Visible = False: TextBox8.Visible = False: TextBox9.Visible = False

TextBox10.Visible = True: TextBox11.Visible = True: TextBox12.Visible = True
TextBox13.Visible = True: TextBox14.Visible = True: TextBox15.Visible = True
TextBox16.Visible = False: TextBox17.Visible = False: TextBox18.Visible = False

ComboBox1.Visible = True: ComboBox2.Visible = True: ComboBox3.Visible = True
ComboBox4.Visible = True: ComboBox5.Visible = True: ComboBox6.Visible = True
ComboBox7.Visible = False: ComboBox8.Visible = False: ComboBox9.Visible = False

TextBox1.SetFocus: Label1.Visible = True: Label2.Visible = True
End If

If OptionButton6.Value = True And OptionButton10.Value = True Then
ComboBox1.Visible = True: ComboBox2.Visible = True: ComboBox3.Visible = True
ComboBox4.Visible = True: ComboBox5.Visible = True: ComboBox6.Visible = True
ComboBox7.Visible = False: ComboBox8.Visible = False: ComboBox9.Visible = False
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
End If

End Sub
Private Sub OptionButton7_Click()
OptionButton10.Enabled = True
If OptionButton7.Value = True And OptionButton10.Value = False Then
ComboBox7.Left = 210: Label2.Left = 210: CmdButton1.Enabled = True
TextBox1.Visible = True: TextBox2.Visible = True: TextBox3.Visible = True
TextBox4.Visible = True: TextBox5.Visible = True: TextBox6.Visible = True
TextBox7.Visible = True: TextBox8.Visible = False: TextBox9.Visible = False

TextBox10.Visible = True: TextBox11.Visible = True: TextBox12.Visible = True
TextBox13.Visible = True: TextBox14.Visible = True: TextBox15.Visible = True
TextBox16.Visible = True: TextBox17.Visible = False: TextBox18.Visible = False

ComboBox1.Visible = True: ComboBox2.Visible = True: ComboBox3.Visible = True
ComboBox4.Visible = True: ComboBox5.Visible = True: ComboBox6.Visible = True
ComboBox7.Visible = True: ComboBox8.Visible = False: ComboBox9.Visible = False

TextBox1.SetFocus: Label1.Visible = True: Label2.Visible = True
End If

If OptionButton7.Value = True And OptionButton10.Value = True Then
ComboBox1.Visible = True: ComboBox2.Visible = True: ComboBox3.Visible = True
ComboBox4.Visible = True: ComboBox5.Visible = True: ComboBox6.Visible = True
ComboBox7.Visible = True: ComboBox8.Visible = False: ComboBox9.Visible = False
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
OptionButton7.Caption = "RUIMTE 7"
End If

End Sub
Private Sub OptionButton8_Click()
OptionButton10.Enabled = True
If OptionButton8.Value = True And OptionButton10.Value = False Then
ComboBox8.Left = 210: Label2.Left = 210: CmdButton1.Enabled = True
TextBox1.Visible = True: TextBox2.Visible = True: TextBox3.Visible = True
TextBox4.Visible = True: TextBox5.Visible = True: TextBox6.Visible = True
TextBox7.Visible = True: TextBox8.Visible = True: TextBox9.Visible = False

TextBox10.Visible = True: TextBox11.Visible = True: TextBox12.Visible = True
TextBox13.Visible = True: TextBox14.Visible = True: TextBox15.Visible = True
TextBox16.Visible = True: TextBox17.Visible = True: TextBox18.Visible = False

ComboBox1.Visible = True: ComboBox2.Visible = True: ComboBox3.Visible = True
ComboBox4.Visible = True: ComboBox5.Visible = True: ComboBox6.Visible = True
ComboBox7.Visible = True: ComboBox8.Visible = True: ComboBox9.Visible = False

TextBox1.SetFocus: Label1.Visible = True: Label2.Visible = True
End If

If OptionButton8.Value = True And OptionButton10.Value = True Then
ComboBox1.Visible = True: ComboBox2.Visible = True: ComboBox3.Visible = True
ComboBox4.Visible = True: ComboBox5.Visible = True: ComboBox6.Visible = True
ComboBox7.Visible = True: ComboBox8.Visible = True: ComboBox9.Visible = False
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
OptionButton7.Caption = "RUIMTE 7": OptionButton8.Caption = "RUIMTE 8"
End If

End Sub
Private Sub OptionButton9_Click()
OptionButton10.Enabled = True
If OptionButton9.Value = True And OptionButton10.Value = False Then
ComboBox9.Left = 210: Label2.Left = 210: CmdButton1.Enabled = True
TextBox1.Visible = True: TextBox2.Visible = True: TextBox3.Visible = True
TextBox4.Visible = True: TextBox5.Visible = True: TextBox6.Visible = True
TextBox7.Visible = True: TextBox8.Visible = True: TextBox9.Visible = True

TextBox10.Visible = True: TextBox11.Visible = True: TextBox12.Visible = True
TextBox13.Visible = True: TextBox14.Visible = True: TextBox15.Visible = True
TextBox16.Visible = True: TextBox17.Visible = True: TextBox18.Visible = True

ComboBox1.Visible = True: ComboBox2.Visible = True: ComboBox3.Visible = True
ComboBox4.Visible = True: ComboBox5.Visible = True: ComboBox6.Visible = True
ComboBox7.Visible = True: ComboBox8.Visible = True: ComboBox9.Visible = True

TextBox1.SetFocus: Label1.Visible = True: Label2.Visible = True
End If

If OptionButton9.Value = True And OptionButton10.Value = True Then
ComboBox1.Visible = True: ComboBox2.Visible = True: ComboBox3.Visible = True
ComboBox4.Visible = True: ComboBox5.Visible = True: ComboBox6.Visible = True
ComboBox7.Visible = True: ComboBox8.Visible = True: ComboBox9.Visible = True
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
OptionButton7.Caption = "RUIMTE 7": OptionButton8.Caption = "RUIMTE 8"
OptionButton9.Caption = "RUIMTE 9"
End If
End Sub
Private Sub OptionButton10_Click()
Label1.Visible = False
Label2.Visible = True: Label2.Left = 84
ComboBox1.Left = 84: ComboBox2.Left = 84: ComboBox3.Left = 84
ComboBox4.Left = 84: ComboBox5.Left = 84: ComboBox6.Left = 84
ComboBox7.Left = 84: ComboBox8.Left = 84: ComboBox9.Left = 84
TextBox1.Visible = False: TextBox2.Visible = False: TextBox3.Visible = False
TextBox4.Visible = False: TextBox5.Visible = False: TextBox6.Visible = False
TextBox7.Visible = False: TextBox8.Visible = False: TextBox9.Visible = False
TextBox10.Visible = False: TextBox11.Visible = False: TextBox12.Visible = False
TextBox13.Visible = False: TextBox14.Visible = False: TextBox15.Visible = False
TextBox16.Visible = False: TextBox17.Visible = False: TextBox18.Visible = False

If OptionButton1.Value = True And OptionButton10.Value = True Then
CmdButton1.Enabled = True: ComboBox1.Visible = True: ComboBox1.SetFocus
OptionButton1.Caption = "RUIMTE 1": Frame3.Caption = "Aanv.Verwarming"
End If
If OptionButton2.Value = True And OptionButton10.Value = True Then
CmdButton1.Enabled = True: ComboBox2.Visible = True: ComboBox1.SetFocus
OptionButton1.Caption = "RUIMTE 1": OptionButton2.Caption = "RUIMTE 2"
Frame3.Caption = "Aanv.Verwarming"
End If
If OptionButton3.Value = True And OptionButton10.Value = True Then
CmdButton1.Enabled = True: ComboBox3.Visible = True: ComboBox1.SetFocus
OptionButton1.Caption = "RUIMTE 1": OptionButton2.Caption = "RUIMTE 2"
OptionButton3.Caption = "RUIMTE 3": Frame3.Caption = "Aanv.Verwarming"
End If
If OptionButton4.Value = True And OptionButton10.Value = True Then
CmdButton1.Enabled = True: ComboBox4.Visible = True: ComboBox1.SetFocus
OptionButton1.Caption = "RUIMTE 1": OptionButton2.Caption = "RUIMTE 2"
OptionButton3.Caption = "RUIMTE 3": OptionButton4.Caption = "RUIMTE 4"
Frame3.Caption = "Aanv.Verwarming"
End If
If OptionButton5.Value = True And OptionButton10.Value = True Then
CmdButton1.Enabled = True: ComboBox5.Visible = True: ComboBox1.SetFocus
OptionButton1.Caption = "RUIMTE 1": OptionButton2.Caption = "RUIMTE 2"
OptionButton3.Caption = "RUIMTE 3": OptionButton4.Caption = "RUIMTE 4"
OptionButton5.Caption = "RUIMTE 5": Frame3.Caption = "Aanv.Verwarming"
End If
If OptionButton6.Value = True And OptionButton10.Value = True Then
CmdButton1.Enabled = True: ComboBox6.Visible = True: ComboBox1.SetFocus
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
Frame3.Caption = "Aanv.Verwarming"
End If
If OptionButton7.Value = True And OptionButton10.Value = True Then
CmdButton1.Enabled = True: ComboBox7.Visible = True: ComboBox1.SetFocus
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
OptionButton7.Caption = "RUIMTE 7": Frame3.Caption = "Aanv.Verwarming"
End If
If OptionButton8.Value = True And OptionButton10.Value = True Then
CmdButton1.Enabled = True: ComboBox8.Visible = True: ComboBox1.SetFocus
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
OptionButton7.Caption = "RUIMTE 7": OptionButton8.Caption = "RUIMTE 8"
Frame3.Caption = "Aanv.Verwarming"
End If
If OptionButton9.Value = True And OptionButton10.Value = True Then
CmdButton1.Enabled = True: ComboBox9.Visible = True: ComboBox1.SetFocus
OptionButton1.Caption = "RUIMTE 1": OptionButton2.Caption = "RUIMTE 2"
OptionButton3.Caption = "RUIMTE 3": OptionButton4.Caption = "RUIMTE 4"
OptionButton5.Caption = "RUIMTE 5": OptionButton6.Caption = "RUIMTE 6"
OptionButton7.Caption = "RUIMTE 7": OptionButton8.Caption = "RUIMTE 8"
OptionButton9.Caption = "RUIMTE 9": Frame3.Caption = "Aanv.Verwarming"
End If
End Sub
Private Sub blok1_Click()
   If blok1.Value = True Then
      nummer = nummer + 1
   Else
      nummer = nummer - 1
   End If
   If nummer > 0 Then
      CmdButton1.Enabled = True
   Else
      CmdButton1.Enabled = False
   End If
End Sub
Private Sub blok2_Click()
If blok2.Value = True Then
      nummer = nummer + 1
   Else
      nummer = nummer - 1
   End If
   If nummer > 0 Then
      CmdButton1.Enabled = True
   Else
      CmdButton1.Enabled = False
   End If
End Sub
Private Sub blok3_Click()
If blok3.Value = True Then
      nummer = nummer + 1
   Else
      nummer = nummer - 1
   End If
   If nummer > 0 Then
      CmdButton1.Enabled = True
   Else
      CmdButton1.Enabled = False
   End If
End Sub
Private Sub blok4_Click()
If blok4.Value = True Then
      nummer = nummer + 1
   Else
      nummer = nummer - 1
   End If
   If nummer > 0 Then
      CmdButton1.Enabled = True
   Else
      CmdButton1.Enabled = False
   End If
End Sub
Private Sub blok5_Click()
If blok5.Value = True Then
      nummer = nummer + 1
   Else
      nummer = nummer - 1
   End If
   If nummer > 0 Then
      CmdButton1.Enabled = True
   Else
      CmdButton1.Enabled = False
   End If
End Sub
Private Sub blok6_Click()
If blok6.Value = True Then
      nummer = nummer + 1
   Else
      nummer = nummer - 1
   End If
   If nummer > 0 Then
      CmdButton1.Enabled = True
   Else
      CmdButton1.Enabled = False
   End If
End Sub
Private Sub blok7_Click()
If blok7.Value = True Then
      nummer = nummer + 1
   Else
      nummer = nummer - 1
   End If
   If nummer > 0 Then
      CmdButton1.Enabled = True
   Else
      CmdButton1.Enabled = False
   End If
End Sub
Private Sub blok8_Click()
If blok8.Value = True Then
      nummer = nummer + 1
   Else
      nummer = nummer - 1
   End If
   If nummer > 0 Then
      CmdButton1.Enabled = True
   Else
      CmdButton1.Enabled = False
   End If
End Sub
Private Sub blok9_Click()
If blok9.Value = True Then
      nummer = nummer + 1
   Else
      nummer = nummer - 1
   End If
   If nummer > 0 Then
      CmdButton1.Enabled = True
   Else
      CmdButton1.Enabled = False
   End If
End Sub
Private Sub blok10_Click()
If blok10.Value = True Then
      nummer = nummer + 1
   Else
      nummer = nummer - 1
   End If
   If nummer > 0 Then
      CmdButton1.Enabled = True
   Else
      CmdButton1.Enabled = False
   End If
End Sub
Private Sub blok12_Click()
If blok12.Value = True Then
      nummer = nummer + 1
   Else
      nummer = nummer - 1
   End If
   If nummer > 0 Then
      CmdButton1.Enabled = True
   Else
      CmdButton1.Enabled = False
   End If
End Sub
Private Sub blok13_Click()
  If blok13.Value = True Then
      nummer = nummer + 1
   Else
      nummer = nummer - 1
   End If
   If nummer > 0 Then
      CmdButton1.Enabled = True
   Else
      CmdButton1.Enabled = False
   End If
End Sub

Private Sub blok100_Click()
If blok100.Value = True Then
      nummer = nummer + 1
   Else
      nummer = nummer - 1
   End If
   If nummer > 0 Then
      CmdButton1.Enabled = True
   Else
      CmdButton1.Enabled = False
   End If
End Sub
Private Sub blok110_Click()
If blok110.Value = True Then
      nummer = nummer + 1
   Else
      nummer = nummer - 1
   End If
   If nummer > 0 Then
      CmdButton1.Enabled = True
   Else
      CmdButton1.Enabled = False
   End If
End Sub
Private Sub blok120_Click()
If blok120.Value = True Then
      nummer = nummer + 1
   Else
      nummer = nummer - 1
   End If
   If nummer > 0 Then
      CmdButton1.Enabled = True
   Else
      CmdButton1.Enabled = False
   End If
End Sub
Private Sub blok130_Click()
If blok130.Value = True Then
      nummer = nummer + 1
   Else
      nummer = nummer - 1
   End If
   If nummer > 0 Then
      CmdButton1.Enabled = True
   Else
      CmdButton1.Enabled = False
   End If
End Sub
Private Sub blok140_Click()
If blok140.Value = True Then
      nummer = nummer + 1
   Else
      nummer = nummer - 1
   End If
   If nummer > 0 Then
      CmdButton1.Enabled = True
   Else
      CmdButton1.Enabled = False
   End If
End Sub
Private Sub blok150_Click()
If blok150.Value = True Then
      nummer = nummer + 1
   Else
      nummer = nummer - 1
   End If
   If nummer > 0 Then
      CmdButton1.Enabled = True
   Else
      CmdButton1.Enabled = False
   End If
If blok150.Value = True Then
blok160.Enabled = False
Else
blok160.Enabled = True
End If
End Sub
Private Sub blok160_Click()
If blok160.Value = True Then
      nummer = nummer + 1
   Else
      nummer = nummer - 1
   End If
   If nummer > 0 Then
      CmdButton1.Enabled = True
   Else
      CmdButton1.Enabled = False
   End If
   
If blok160.Value = True Then
blok150.Enabled = False
Else
blok150.Enabled = True
End If
   
End Sub
Private Sub blok170_Click()
If blok170.Value = True Then
      nummer = nummer + 1
   Else
      nummer = nummer - 1
   End If
   If nummer > 0 Then
      CmdButton1.Enabled = True
   Else
      CmdButton1.Enabled = False
   End If
   
If blok170.Value = True Then
blok180.Enabled = False
Else
blok180.Enabled = True
End If
   
End Sub
Private Sub blok180_Click()
If blok180.Value = True Then
      nummer = nummer + 1
   Else
      nummer = nummer - 1
   End If
   If nummer > 0 Then
      CmdButton1.Enabled = True
   Else
      CmdButton1.Enabled = False
   End If
   
If blok180.Value = True Then
blok170.Enabled = False
Else
blok170.Enabled = True
End If
   
End Sub
Private Sub blok190_Click()
If blok190.Value = True Then
      nummer = nummer + 1
   Else
      nummer = nummer - 1
 End If
   If nummer > 0 Then
      CmdButton1.Enabled = True
   Else
      CmdButton1.Enabled = False
   End If

End Sub
Private Sub CmdButton1_Click()
Dim newLayer As AcadLayer
On Error Resume Next
Set newLayer = ThisDrawing.Layers.Add("3")
ThisDrawing.ActiveLayer = newLayer
Update


If TextBox1.Text = "" And TextBox1.Visible = True Then
MsgBox "Je bent vergeten een tekort in te vullen...!!!"
For I = 0 To MultiPage2.Count - 1
MultiPage2.Value = I
Next I
TextBox1.SetFocus
Exit Sub
End If

If ComboBox1.Value = "" And ComboBox1.Visible = True Then
MsgBox "Je bent vergeten een ruimtenaam te selecteren...!!!"
For I = 0 To MultiPage2.Count - 1
MultiPage2.Value = I
Next I
ComboBox1.SetFocus
Exit Sub
End If

If TextBox2.Text = "" And TextBox2.Visible = True Then
MsgBox "Je bent vergeten een tekort in te vullen...!!!"
For I = 0 To MultiPage2.Count - 1
MultiPage2.Value = I
Next I
TextBox2.SetFocus
Exit Sub
End If

If ComboBox2.Value = "" And ComboBox2.Visible = True Then
MsgBox "Je bent vergeten een ruimtenaam te selecteren...!!!"
For I = 0 To MultiPage2.Count - 1
MultiPage2.Value = I
Next I
ComboBox2.SetFocus
Exit Sub
End If

If TextBox3.Text = "" And TextBox3.Visible = True Then
MsgBox "Je bent vergeten een tekort in te vullen...!!!"
For I = 0 To MultiPage2.Count - 1
MultiPage2.Value = I
Next I
TextBox3.SetFocus
Exit Sub
End If

If ComboBox3.Value = "" And ComboBox3.Visible = True Then
MsgBox "Je bent vergeten een ruimtenaam te selecteren...!!!"
For I = 0 To MultiPage2.Count - 1
MultiPage2.Value = I
Next I
ComboBox3.SetFocus
Exit Sub
End If

If TextBox4.Text = "" And TextBox4.Visible = True Then
MsgBox "Je bent vergeten een tekort in te vullen...!!!"
For I = 0 To MultiPage2.Count - 1
MultiPage2.Value = I
Next I
TextBox4.SetFocus
Exit Sub
End If

If ComboBox4.Value = "" And ComboBox4.Visible = True Then
MsgBox "Je bent vergeten een ruimtenaam te selecteren...!!!"
For I = 0 To MultiPage2.Count - 1
MultiPage2.Value = I
Next I
ComboBox4.SetFocus
Exit Sub
End If

If TextBox5.Text = "" And TextBox5.Visible = True Then
MsgBox "Je bent vergeten een tekort in te vullen...!!!"
For I = 0 To MultiPage2.Count - 1
MultiPage2.Value = I
Next I
TextBox5.SetFocus
Exit Sub
End If

If ComboBox5.Value = "" And ComboBox5.Visible = True Then
MsgBox "Je bent vergeten een ruimtenaam te selecteren...!!!"
For I = 0 To MultiPage2.Count - 1
MultiPage2.Value = I
Next I
ComboBox5.SetFocus
Exit Sub
End If

If TextBox6.Text = "" And TextBox6.Visible = True Then
MsgBox "Je bent vergeten een tekort in te vullen...!!!"
For I = 0 To MultiPage2.Count - 1
MultiPage2.Value = I
Next I
TextBox6.SetFocus
Exit Sub
End If

If ComboBox6.Value = "" And ComboBox6.Visible = True Then
MsgBox "Je bent vergeten een ruimtenaam te selecteren...!!!"
For I = 0 To MultiPage2.Count - 1
MultiPage2.Value = I
Next I
ComboBox6.SetFocus
Exit Sub
End If

If TextBox7.Text = "" And TextBox7.Visible = True Then
MsgBox "Je bent vergeten een tekort in te vullen...!!!"
For I = 0 To MultiPage2.Count - 1
MultiPage2.Value = I
Next I
TextBox7.SetFocus
Exit Sub
End If

If ComboBox7.Value = "" And ComboBox7.Visible = True Then
MsgBox "Je bent vergeten een ruimtenaam te selecteren...!!!"
For I = 0 To MultiPage2.Count - 1
MultiPage2.Value = I
Next I
ComboBox7.SetFocus
Exit Sub
End If

If TextBox8.Text = "" And TextBox8.Visible = True Then
MsgBox "Je bent vergeten een tekort in te vullen...!!!"
For I = 0 To MultiPage2.Count - 1
MultiPage2.Value = I
Next I
TextBox8.SetFocus
Exit Sub
End If

If ComboBox8.Value = "" And ComboBox8.Visible = True Then
MsgBox "Je bent vergeten een ruimtenaam te selecteren...!!!"
For I = 0 To MultiPage2.Count - 1
MultiPage2.Value = I
Next I
ComboBox8.SetFocus
Exit Sub
End If

If TextBox9.Text = "" And TextBox9.Visible = True Then
MsgBox "Je bent vergeten een tekort in te vullen...!!!"
For I = 0 To MultiPage2.Count - 1
MultiPage2.Value = I
Next I
TextBox9.SetFocus
Exit Sub
End If

If ComboBox9.Value = "" And ComboBox9.Visible = True Then
MsgBox "Je bent vergeten een ruimtenaam te selecteren...!!!"
For I = 0 To MultiPage2.Count - 1
MultiPage2.Value = I
Next I
ComboBox9.SetFocus
Exit Sub
End If

'blokken.Hide


Call Schaal(scaal)
ThisDrawing.SetVariable "osmode", 1
Dim PBEGINZEROnul As Variant
Dim pbeginzero(0 To 2) As Double

If blok1.Value = True Or blok2.Value = True Or blok3.Value = True Or _
   blok4.Value = True Or blok5.Value = True Or blok6.Value = True Or blok7.Value = True Or _
   blok8.Value = True Or blok9.Value = True Or blok10.Value = True Or _
   blok12.Value = True Or blok13.Value = True Then
   blokken.Hide
   PBEGINZEROnul = ThisDrawing.Utility.GetPoint(, "Plaats STARTPUNT")
   pbeginzero(0) = PBEGINZEROnul(0)
   pbeginzero(1) = PBEGINZEROnul(1) - (77 * scaal)
    If Err Then
    'Call reset2
    blokken.Show
    Exit Sub
    End If
End If
     
      
       

If blok5.Value = True Then
       pbeginzero(0) = pbeginzero(0)
       pbeginzero(1) = pbeginzero(1) + (77 * scaal)
       Call blok51(pbeginzero)
       End If
       
If blok13.Value = True Then
       pbeginzero(0) = pbeginzero(0)
       pbeginzero(1) = pbeginzero(1) + (77 * scaal)
       Call blok131(pbeginzero)
       End If
       
If blok1.Value = True Then
       pbeginzero(0) = pbeginzero(0)
       pbeginzero(1) = pbeginzero(1) + (77 * scaal)
       Call blok11(pbeginzero)
       End If

If blok2.Value = True Then
       pbeginzero(0) = pbeginzero(0)
       pbeginzero(1) = pbeginzero(1) + (77 * scaal)
       Call blok21(pbeginzero)
       End If
If blok6.Value = True Then
       pbeginzero(0) = pbeginzero(0)
       pbeginzero(1) = pbeginzero(1) + (77 * scaal)
       Call blok61(pbeginzero)
       End If
If blok7.Value = True Then
       pbeginzero(0) = pbeginzero(0)
       pbeginzero(1) = pbeginzero(1) + (77 * scaal)
       Call blok71(pbeginzero)
       End If

'If blok12.Value = True Then
'       PBEGINZERO(0) = PBEGINZERO(0)
'       PBEGINZERO(1) = PBEGINZERO(1) + (77 * scaal)
'       Call blok121(PBEGINZERO)
'       End If
       

Dim attributen As Variant
Dim element As AcadEntity
Dim attribuut As AcadAttributeReference
Dim symbool As AcadBlockReference

ThisDrawing.SetVariable "osmode", 1
blokken.Hide
On Error Resume Next

If OptionButton1 = True Then
     If blok1.Value = False And blok2.Value = False And blok3.Value = False And _
       blok4.Value = False And blok5.Value = False And blok6.Value = False And blok7.Value = False And _
       blok8.Value = False And blok9.Value = False And blok10.Value = False And blok12.Value = False Then
       pBEGINZEROstart = ThisDrawing.Utility.GetPoint(, "Plaats STARTPUNT")
       pbeginzero(0) = pBEGINZEROstart(0)
       pbeginzero(1) = pBEGINZEROstart(1)
          
     Else
       pbeginzero(0) = pbeginzero(0)
       pbeginzero(1) = pbeginzero(1) + (77 * scaal)
    End If
    
If OptionButton10.Value = False Then
Tbestand = "C:\ACAD2002\DWG\bltekor.dwg"
Else
Tbestand = "C:\ACAD2002\DWG\avbltekor.dwg"
End If
Set blockRefObj = ThisDrawing.ModelSpace.InsertBlock(pbeginzero, Tbestand, scaal, scaal, 1, 0)
If Err Then
    blokken.Show
    Exit Sub
    End If
Call optie1
End If

If OptionButton2 = True Or OptionButton3 = True Then
       If blok1.Value = False And blok2.Value = False And blok3.Value = False And _
       blok4.Value = False And blok5.Value = False And blok6.Value = False And blok7.Value = False And _
       blok8.Value = False And blok9.Value = False And blok10.Value = False And blok12.Value = False Then
       pBEGINZEROstart = ThisDrawing.Utility.GetPoint(, "Plaats STARTPUNT")
       pbeginzero(0) = pBEGINZEROstart(0)
       pbeginzero(1) = pBEGINZEROstart(1)
          
     Else
       pbeginzero(0) = pbeginzero(0)
       pbeginzero(1) = pbeginzero(1) + (77 * scaal)
    End If

If OptionButton10.Value = False Then
Tbestand = "C:\ACAD2002\DWG\bltekor1.dwg"
Else
Tbestand = "C:\ACAD2002\DWG\avbltekor1.dwg"
End If

Set blockRefObj = ThisDrawing.ModelSpace.InsertBlock(pbeginzero, Tbestand, scaal, scaal, 1, 0)
If Err Then
    blokken.Show
    Exit Sub
    End If
Call optie2
End If

If OptionButton4 = True Or OptionButton5 = True Or OptionButton6 = True Then
       If blok1.Value = False And blok2.Value = False And blok3.Value = False And _
       blok4.Value = False And blok5.Value = False And blok6.Value = False And blok7.Value = False And _
       blok8.Value = False And blok9.Value = False And blok10.Value = False And blok12.Value = False Then
       pBEGINZEROstart = ThisDrawing.Utility.GetPoint(, "Plaats STARTPUNT")
       pbeginzero(0) = pBEGINZEROstart(0)
       pbeginzero(1) = pBEGINZEROstart(1)
          
     Else
       pbeginzero(0) = pbeginzero(0)
       pbeginzero(1) = pbeginzero(1) + (77 * scaal)
    End If
    
If OptionButton10.Value = False Then
Tbestand = "C:\ACAD2002\DWG\bltekor2.dwg"
Else
Tbestand = "C:\ACAD2002\DWG\avbltekor2.dwg"
End If
Set blockRefObj = ThisDrawing.ModelSpace.InsertBlock(pbeginzero, Tbestand, scaal, scaal, 1, 0)
If Err Then
    blokken.Show
    Exit Sub
    End If
Call optie3
End If

If OptionButton7 = True Or OptionButton8 = True Or OptionButton9 = True Then
       If blok1.Value = False And blok2.Value = False And blok3.Value = False And _
       blok4.Value = False And blok5.Value = False And blok6.Value = False And blok7.Value = False And _
       blok8.Value = False And blok9.Value = False And blok10.Value = False And blok12.Value = False Then
       pBEGINZEROstart = ThisDrawing.Utility.GetPoint(, "Plaats STARTPUNT")
       pbeginzero(0) = pBEGINZEROstart(0)
       pbeginzero(1) = pBEGINZEROstart(1)
     Else
       pbeginzero(0) = pbeginzero(0)
       pbeginzero(1) = pbeginzero(1) + (77 * scaal)
    End If
    
If OptionButton10.Value = False Then
Tbestand = "C:\ACAD2002\DWG\bltekor3.dwg"
Else
Tbestand = "C:\ACAD2002\DWG\avbltekor3.dwg"
End If
Set blockRefObj = ThisDrawing.ModelSpace.InsertBlock(pbeginzero, Tbestand, scaal, scaal, 1, 0)
If Err Then
    blokken.Show
    Exit Sub
    End If
Call optie4
End If
Update
'--------------DEFINITIEF OF REVISIE-OF VOORLOPIG OF TER GOEDKEURING OF NAREGELEN--of UITVOERING-----------------------------------------
checkdef = 0
If blok3.Value = True And OptionButton1 = True Then
       pbeginzero(0) = pbeginzero(0)
       pbeginzero(1) = pbeginzero(1) + (113.7 * scaal)
       checkdef = 1
       Call blok31(pbeginzero) 'blok definitief
       End If

If OptionButton2 = True Or OptionButton3 = True Then tekorten23 = 1
If blok3.Value = True And tekorten23 = 1 Then
       pbeginzero(0) = pbeginzero(0)
       pbeginzero(1) = pbeginzero(1) + (162.7 * scaal) '162.7
       checkdef = 1
       Call blok31(pbeginzero) 'blok definitief
       End If

If OptionButton4 = True Or OptionButton5 = True Or OptionButton6 = True Then tekorten456 = 1
If blok3.Value = True And tekorten456 = 1 Then
       pbeginzero(0) = pbeginzero(0)
       pbeginzero(1) = pbeginzero(1) + (238.7 * scaal)
       checkdef = 1
       Call blok31(pbeginzero) 'blok definitief
       End If
       
If OptionButton7 = True Or OptionButton8 = True Or OptionButton9 = True Then tekorten789 = 1
If blok3.Value = True And tekorten789 = 1 Then
       pbeginzero(0) = pbeginzero(0)
       pbeginzero(1) = pbeginzero(1) + (305.7 * scaal)
       checkdef = 1
       Call blok31(pbeginzero) 'blok definitief
       End If

If checkdef = 0 And blok3.Value = True Then
       pbeginzero(0) = pbeginzero(0)
       pbeginzero(1) = pbeginzero(1) + (77 * scaal)
       Call blok31(pbeginzero) 'blok definitief
       End If
'----------------------------------------------------------------------------
checkrev = 0
If blok4.Value = True And OptionButton1 = True Then
       pbeginzero(0) = pbeginzero(0)
       pbeginzero(1) = pbeginzero(1) + (113.7 * scaal)
       checkrev = 1
       Call blok41(pbeginzero) 'blok revisie
       End If

If blok4.Value = True And tekorten23 = 1 Then
       pbeginzero(0) = pbeginzero(0)
       pbeginzero(1) = pbeginzero(1) + (162.7 * scaal)
       checkrev = 1
       Call blok41(pbeginzero) 'blok revisie
       End If

If blok4.Value = True And tekorten456 = 1 Then
       pbeginzero(0) = pbeginzero(0)
       pbeginzero(1) = pbeginzero(1) + (238.7 * scaal)
       checkrev = 1
       Call blok41(pbeginzero) 'blok revisie
       End If
       
If blok4.Value = True And tekorten789 = 1 Then
       pbeginzero(0) = pbeginzero(0)
       pbeginzero(1) = pbeginzero(1) + (305.7 * scaal)
       checkrev = 1
       Call blok41(pbeginzero) 'blok revisie
       End If

If checkrev = 0 And blok4.Value = True Then
       pbeginzero(0) = pbeginzero(0)
       pbeginzero(1) = pbeginzero(1) + (77 * scaal)
       Call blok41(pbeginzero)
       End If
       
       
checkgoed = 0
If blok8.Value = True And OptionButton1 = True Then
       pbeginzero(0) = pbeginzero(0)
       pbeginzero(1) = pbeginzero(1) + (113.7 * scaal)
       checkgoed = 1
       Call blok81(pbeginzero) 'blok Ter Goedkeuring
       End If

If OptionButton2 = True Or OptionButton3 = True Then tekorten23 = 1
If blok8.Value = True And tekorten23 = 1 Then
       pbeginzero(0) = pbeginzero(0)
       pbeginzero(1) = pbeginzero(1) + (162.7 * scaal) '162.7
       checkgoed = 1
       Call blok81(pbeginzero) 'blok Ter Goedkeuring
       End If

If OptionButton4 = True Or OptionButton5 = True Or OptionButton6 = True Then tekorten456 = 1
If blok8.Value = True And tekorten456 = 1 Then
       pbeginzero(0) = pbeginzero(0)
       pbeginzero(1) = pbeginzero(1) + (238.7 * scaal)
       checkgoed = 1
       Call blok81(pbeginzero) 'blok Ter Goedkeuring
       End If
       
If OptionButton7 = True Or OptionButton8 = True Or OptionButton9 = True Then tekorten789 = 1
If blok8.Value = True And tekorten789 = 1 Then
       pbeginzero(0) = pbeginzero(0)
       pbeginzero(1) = pbeginzero(1) + (305.7 * scaal)
       checkgoed = 1
       Call blok81(pbeginzero) 'blok Ter Goedkeuring
       End If

If checkgoed = 0 And blok8.Value = True Then
       pbeginzero(0) = pbeginzero(0)
       pbeginzero(1) = pbeginzero(1) + (77 * scaal)
       Call blok81(pbeginzero) 'blok Ter Goedkeuring
       End If
       
       
checkvoor = 0
If blok9.Value = True And OptionButton1 = True Then
       pbeginzero(0) = pbeginzero(0)
       pbeginzero(1) = pbeginzero(1) + (113.7 * scaal)
       checkvoor = 1
       Call blok91(pbeginzero) 'blok voorlopig
       End If

If OptionButton2 = True Or OptionButton3 = True Then tekorten23 = 1
If blok9.Value = True And tekorten23 = 1 Then
       pbeginzero(0) = pbeginzero(0)
       pbeginzero(1) = pbeginzero(1) + (162.7 * scaal) '162.7
       checkvoor = 1
       Call blok91(pbeginzero) 'blok voorlopig
       End If

If OptionButton4 = True Or OptionButton5 = True Or OptionButton6 = True Then tekorten456 = 1
If blok9.Value = True And tekorten456 = 1 Then
       pbeginzero(0) = pbeginzero(0)
       pbeginzero(1) = pbeginzero(1) + (238.7 * scaal)
       checkvoor = 1
       Call blok91(pbeginzero) 'blok voorlopig
       End If
       
If OptionButton7 = True Or OptionButton8 = True Or OptionButton9 = True Then tekorten789 = 1
If blok9.Value = True And tekorten789 = 1 Then
       pbeginzero(0) = pbeginzero(0)
       pbeginzero(1) = pbeginzero(1) + (305.7 * scaal)
       checkvoor = 1
       Call blok91(pbeginzero) 'blok voorlopig
       End If

If checkvoor = 0 And blok9.Value = True Then
       pbeginzero(0) = pbeginzero(0)
       pbeginzero(1) = pbeginzero(1) + (77 * scaal)
       Call blok91(pbeginzero) 'blok voorlopig
       End If
       
checkuitvoering = 0
If blok12.Value = True And OptionButton1 = True Then
       pbeginzero(0) = pbeginzero(0)
       pbeginzero(1) = pbeginzero(1) + (113.7 * scaal)
       checkuitvoering = 1
       Call blok121(pbeginzero) 'blok checkuitvoering
       End If

If OptionButton2 = True Or OptionButton3 = True Then tekorten23 = 1
If blok12.Value = True And tekorten23 = 1 Then
       pbeginzero(0) = pbeginzero(0)
       pbeginzero(1) = pbeginzero(1) + (162.7 * scaal) '162.7
       checkuitvoering = 1
       Call blok121(pbeginzero) 'blok checkuitvoering
       End If

If OptionButton4 = True Or OptionButton5 = True Or OptionButton6 = True Then tekorten456 = 1
If blok12.Value = True And tekorten456 = 1 Then
       pbeginzero(0) = pbeginzero(0)
       pbeginzero(1) = pbeginzero(1) + (238.7 * scaal)
       checkuitvoering = 1
       Call blok121(pbeginzero) 'blok checkuitvoering
       End If
       
If OptionButton7 = True Or OptionButton8 = True Or OptionButton9 = True Then tekorten789 = 1
If blok12.Value = True And tekorten789 = 1 Then
       pbeginzero(0) = pbeginzero(0)
       pbeginzero(1) = pbeginzero(1) + (305.7 * scaal)
       checkuitvoering = 1
       Call blok121(pbeginzero) 'blok checkuitvoering
       End If

If checkuitvoering = 0 And blok12.Value = True Then
       pbeginzero(0) = pbeginzero(0)
       pbeginzero(1) = pbeginzero(1) + (77 * scaal)
       Call blok121(pbeginzero) 'blok checkuitvoering
       End If
       
       
If checkdef = 1 Or checkrev = 1 Or checkgoed = 1 Or checkvoor = 1 Or checkuitvoering = 1 Then hh = 1
checknaregelen = 0

If hh <> 1 Then
 If blok10.Value = True And OptionButton1 = True Then
       pbeginzero(0) = pbeginzero(0)
       pbeginzero(1) = pbeginzero(1) + (113.7 * scaal)
       checknaregelen = 1
       Call blok101(pbeginzero) 'blok voorlopig
       End If

 If OptionButton2 = True Or OptionButton3 = True Then tekorten23 = 1
 If blok10.Value = True And tekorten23 = 1 Then
       pbeginzero(0) = pbeginzero(0)
       pbeginzero(1) = pbeginzero(1) + (162.7 * scaal) '162.7
       checknaregelen = 1
       Call blok101(pbeginzero) 'blok voorlopig
       End If

 If OptionButton4 = True Or OptionButton5 = True Or OptionButton6 = True Then tekorten456 = 1
 If blok10.Value = True And tekorten456 = 1 Then
       pbeginzero(0) = pbeginzero(0)
       pbeginzero(1) = pbeginzero(1) + (238.7 * scaal)
       checknaregelen = 1
       Call blok101(pbeginzero) 'blok voorlopig
       End If
       
 If OptionButton7 = True Or OptionButton8 = True Or OptionButton9 = True Then tekorten789 = 1
 If blok10.Value = True And tekorten789 = 1 Then
       pbeginzero(0) = pbeginzero(0)
       pbeginzero(1) = pbeginzero(1) + (305.7 * scaal)
       checknaregelen = 1
       Call blok101(pbeginzero) 'blok voorlopig
       End If
End If

   
   If checknaregelen = 0 And blok10.Value = True Then
       pbeginzero(0) = pbeginzero(0)
       pbeginzero(1) = pbeginzero(1) + (77 * scaal)
       Call blok101(pbeginzero) 'blok voorlopig
       End If

'-----------------------------------------------------------------
'blok bl-bouwk vullen

If blokken.CheckBox1.Value = True Then
        Call bouwk
        Dim element10
        For Each element10 In ThisDrawing.ModelSpace
              If element10.ObjectName = "AcDbBlockReference" Then
              If UCase(element10.Name) = "BL-BOUWK" Then
              Set symbool = element10
                If symbool.HasAttributes Then
                attributen = symbool.GetAttributes
                For I = LBound(attributen) To UBound(attributen)
                Set attribuut = attributen(I)
                If attribuut.TagString = "BOUWDATUM" Then attribuut.textstring = UCase(blokken.TextBox19)
                If attribuut.TagString = "BOUWNAAM" Then attribuut.textstring = UCase(blokken.TextBox20)
                
               Next I
        
              End If
              End If
              End If
        Next element10
End If

'blok bouwnummer vullen
If blokken.CheckBox2.Value = True Then
      Call bouwn
      Dim element11
      For Each element11 In ThisDrawing.ModelSpace
          If element11.ObjectName = "AcDbBlockReference" Then
          If UCase(element11.Name) = "BOUWNUMMER" Then
          Set symbool = element11
            If symbool.HasAttributes Then
            attributen = symbool.GetAttributes
            For k = LBound(attributen) To UBound(attributen)
            Set attribuut = attributen(k)
            If attribuut.TagString = "BOUWNUMMER" Then attribuut.textstring = UCase(blokken.TextBox21)
            If attribuut.TagString = "WONINGTYPE" Then attribuut.textstring = UCase(blokken.TextBox22)
            
           Next k
    
          End If
          End If
          End If
    Next element11
End If
Update
       
ThisDrawing.SetVariable "osmode", 0
If blok100.Value = True Then Call blok1000
If blok110.Value = True Then Call blok1100
If blok120.Value = True Then Call blok1200
If blok130.Value = True Then Call blok1300
If blok140.Value = True Then Call blok1400
If blok150.Value = True Then Call blok1500
If blok160.Value = True Then Call blok1600
If blok170.Value = True Then Call blok1700
If blok180.Value = True Then Call blok1800
If blok190.Value = True Then Call blok1900

Call RESET
End Sub
Private Sub bouwk()
blokken.Hide
On Error Resume Next
Call Schaal(scaal)
ThisDrawing.SetVariable "osmode", 1
Dim pbegin7 As Variant
pbegin7 = ThisDrawing.Utility.GetPoint(, "Plaats het blok -Bouwkundige tekening van de klant- ")
Dim bestand As String
bestand = "C:\acad2002\dwg\bl-bouwk.dwg"
Set blockRefObj = ThisDrawing.ModelSpace.InsertBlock(pbegin7, bestand, scaal, scaal, 1, 0)
ThisDrawing.SetVariable "osmode", 0
End Sub
Private Sub bouwn()
blokken.Hide
On Error Resume Next
Call Schaal(scaal)
ThisDrawing.SetVariable "osmode", 1
Dim pbegin7 As Variant
pbegin7 = ThisDrawing.Utility.GetPoint(, "Plaats het blok -Bouwnummer ~ Type woning- ")
Dim bestand As String
bestand = "C:\acad2002\dwg\bouwnummer.dwg"
Set blockRefObj = ThisDrawing.ModelSpace.InsertBlock(pbegin7, bestand, scaal, scaal, 1, 0)
ThisDrawing.SetVariable "osmode", 0
End Sub
Private Sub CancelButton_Click()
Call RESET
blokken.Hide
End Sub
Private Sub CommandButton1_Click()
Call reset2
End Sub
Sub RESET()
ComboBox1.Value = Clear: ComboBox2.Value = Clear: ComboBox3.Value = Clear:
ComboBox4.Value = Clear: ComboBox5.Value = Clear: ComboBox6.Value = Clear:
ComboBox7.Value = Clear: ComboBox8.Value = Clear: ComboBox9.Value = Clear:
TextBox1.Visible = False: TextBox2.Visible = False: TextBox3.Visible = False
TextBox4.Visible = False: TextBox5.Visible = False: TextBox6.Visible = False
TextBox7.Visible = False: TextBox8.Visible = False: TextBox9.Visible = False
TextBox10.Visible = False: TextBox11.Visible = False: TextBox12.Visible = False
TextBox13.Visible = False: TextBox14.Visible = False: TextBox15.Visible = False
TextBox16.Visible = False: TextBox17.Visible = False: TextBox18.Visible = False
blok1.Value = False: blok2.Value = False: blok3.Value = False
blok4.Value = False: blok5.Value = False: blok6.Value = False: blok7.Value = False
blok8.Value = False: blok9.Value = False: blok10.Value = False
blok13.Value = False
blok100.Value = False: blok110.Value = False: blok120.Value = False
blok130.Value = False: blok140.Value = False: blok150.Value = False
blok160.Value = False: blok190.Value = False
OptionButton1 = False: OptionButton2 = False: OptionButton3 = False
OptionButton4 = False: OptionButton5 = False: OptionButton6 = False
OptionButton7 = False: OptionButton8 = False: OptionButton9 = False
CmdButton1.Enabled = False
TextBox1 = Clear: TextBox2 = Clear: TextBox3 = Clear: TextBox4 = Clear: TextBox5 = Clear
TextBox6 = Clear: TextBox7 = Clear: TextBox8 = Clear: TextBox9 = Clear: TextBox10 = Clear
TextBox11 = Clear: TextBox12 = Clear: TextBox13 = Clear: TextBox14 = Clear: TextBox15 = Clear
TextBox16 = Clear: TextBox17 = Clear: TextBox18 = Clear: TextBox19 = Clear: TextBox20 = Clear
TextBox21 = Clear: TextBox22 = Clear: Label1.Visible = False: Label2.Visible = False
ComboBox1.Visible = False: ComboBox2.Visible = False: ComboBox3.Visible = False:
ComboBox4.Visible = False: ComboBox5.Visible = False: ComboBox6.Visible = False:
ComboBox7.Visible = False: ComboBox8.Visible = False: ComboBox9.Visible = False
ThisDrawing.SetVariable "osmode", 0
checkdef = 0: checkrev = 0
tekorten23 = 0: tekorten456 = 0: tekorten789 = 0
OptionButton10 = False
OptionButton10.Enabled = False
ComboBox1.Left = 210: Label2.Left = 210
ComboBox2.Left = 210: ComboBox3.Left = 210: ComboBox4.Left = 210
ComboBox5.Left = 210: ComboBox6.Left = 210: ComboBox7.Left = 210
ComboBox8.Left = 210: ComboBox9.Left = 210
blokken.CheckBox1 = False
blokken.CheckBox2 = False
Unload Me
'ThisDrawing.SendCommand "vbaunload" & vbCr & "blokken" & vbCr
End Sub
Sub reset2()
ComboBox1.Value = Clear: ComboBox2.Value = Clear: ComboBox3.Value = Clear:
ComboBox4.Value = Clear: ComboBox5.Value = Clear: ComboBox6.Value = Clear:
ComboBox7.Value = Clear: ComboBox8.Value = Clear: ComboBox9.Value = Clear:
TextBox1.Visible = False: TextBox2.Visible = False: TextBox3.Visible = False
TextBox4.Visible = False: TextBox5.Visible = False: TextBox6.Visible = False
TextBox7.Visible = False: TextBox8.Visible = False: TextBox9.Visible = False
TextBox10.Visible = False: TextBox11.Visible = False: TextBox12.Visible = False
TextBox13.Visible = False: TextBox14.Visible = False: TextBox15.Visible = False
TextBox16.Visible = False: TextBox17.Visible = False: TextBox18.Visible = False
blok1.Value = False: blok2.Value = False: blok3.Value = False
blok4.Value = False: blok5.Value = False: blok6.Value = False: blok7.Value = False
blok8.Value = False: blok9.Value = False: blok10.Value = False: blok12.Value = False
blok13.Value = False
blok100.Value = False: blok110.Value = False: blok120.Value = False
blok130.Value = False: blok140.Value = False: blok150.Value = False
blok160.Value = False: blok170.Value = False: blok180.Value = False: blok190.Value = False
OptionButton1 = False: OptionButton2 = False: OptionButton3 = False
OptionButton4 = False: OptionButton5 = False: OptionButton6 = False
OptionButton7 = False: OptionButton8 = False: OptionButton9 = False
CmdButton1.Enabled = False
TextBox1 = Clear: TextBox2 = Clear: TextBox3 = Clear: TextBox4 = Clear: TextBox5 = Clear
TextBox6 = Clear: TextBox7 = Clear: TextBox8 = Clear: TextBox9 = Clear: TextBox10 = Clear
TextBox11 = Clear: TextBox12 = Clear: TextBox13 = Clear: TextBox14 = Clear: TextBox15 = Clear
TextBox16 = Clear: TextBox17 = Clear: TextBox18 = Clear: TextBox19 = Clear: TextBox20 = Clear
TextBox21 = Clear: TextBox22 = Clear: Label1.Visible = False: Label2.Visible = False
ComboBox1.Visible = False: ComboBox2.Visible = False: ComboBox3.Visible = False:
ComboBox4.Visible = False: ComboBox5.Visible = False: ComboBox6.Visible = False:
ComboBox7.Visible = False: ComboBox8.Visible = False: ComboBox9.Visible = False
checkdef = 0: checkrev = 0
tekorten23 = 0: tekorten456 = 0: tekorten789 = 0
For z = 0 To MultiPage2.Count - 1
MultiPage2.Value = z - 1
Next z
OptionButton10 = False
OptionButton10.Enabled = False
ComboBox1.Left = 210: Label2.Left = 210
ComboBox2.Left = 210: ComboBox3.Left = 210: ComboBox4.Left = 210
ComboBox5.Left = 210: ComboBox6.Left = 210: ComboBox7.Left = 210
ComboBox8.Left = 210: ComboBox9.Left = 210
OptionButton1.Caption = "1 Radiator": OptionButton2.Caption = "2 Radiatoren"
OptionButton3.Caption = "3 Radiatoren": OptionButton4.Caption = "4 Radiatoren"
OptionButton5.Caption = "5 Radiatoren": OptionButton6.Caption = "6 Radiatoren"
OptionButton7.Caption = "7 Radiatoren": OptionButton8.Caption = "8 Radiatoren"
OptionButton9.Caption = "9 Radiatoren"
Frame3.Caption = "Radiator blokken"
blokken.CheckBox1 = False
blokken.CheckBox2 = False
End Sub

Sub berekenpunt()

End Sub
Sub blok11(pbeginzero)
blokken.Hide
On Error Resume Next
Call Schaal(scaal)
Dim blockRefObj As Object
Dim bestand As String
bestand = "C:\acad2002\dwg\BL-hr.dwg"
Set blockRefObj = ThisDrawing.ModelSpace.InsertBlock(pbeginzero, bestand, scaal, scaal, 1, 0)



If Err Then
    blokken.Show
    Exit Sub
    End If
Update
End Sub
Sub blok21(pbeginzero)
blokken.Hide
On Error Resume Next
Call Schaal(scaal)
Dim bestand As String


bestand = "C:\acad2002\dwg\Bl-bouw.dwg"
Set blockRefObj = ThisDrawing.ModelSpace.InsertBlock(pbeginzero, bestand, scaal, scaal, 1, 0)
If Err Then
    blokken.Show
    Exit Sub
    End If
Update
End Sub
Sub blok31(pbeginzero)
blokken.Hide

On Error Resume Next
Call Schaal(scaal)
Dim bestand As String
bestand = "C:\acad2002\dwg\definitief2.dwg"

Dim blockRefObj
Set blockRefObj = ThisDrawing.ModelSpace.InsertBlock(pbeginzero, bestand, scaal, scaal, 1, 0)
If Err Then
    blokken.Show
    Exit Sub
    End If
Update
End Sub
Sub blok41(pbeginzero)
blokken.Hide
On Error Resume Next
Call Schaal(scaal)
Dim bestand As String
bestand = "C:\acad2002\dwg\Bl-revisie.dwg"
Set blockRefObj = ThisDrawing.ModelSpace.InsertBlock(pbeginzero, bestand, scaal, scaal, 1, 0)
If Err Then
    blokken.Show
    Exit Sub
    End If
Update
End Sub
Sub blok51(pbeginzero)
blokken.Hide
On Error Resume Next
Call Schaal(scaal)
Dim bestand As String
bestand = "C:\acad2002\dwg\Bl-krimp.dwg"
Set blockRefObj = ThisDrawing.ModelSpace.InsertBlock(pbeginzero, bestand, scaal, scaal, 1, 0)
If Err Then
    blokken.Show
    Exit Sub
    End If
Update
End Sub
Sub blok61(pbeginzero)
blokken.Hide
On Error Resume Next
Call Schaal(scaal)
Dim bestand As String
bestand = "C:\acad2002\dwg\Bl-exp.dwg"
Set blockRefObj = ThisDrawing.ModelSpace.InsertBlock(pbeginzero, bestand, scaal, scaal, 1, 0)
If Err Then
    blokken.Show
    Exit Sub
    End If
Update
End Sub
Sub blok71(pbeginzero)
blokken.Hide
On Error Resume Next
Call Schaal(scaal)
Dim bestand As String
bestand = "C:\acad2002\dwg\Bl-keuk.dwg"
Set blockRefObj = ThisDrawing.ModelSpace.InsertBlock(pbeginzero, bestand, scaal, scaal, 1, 0)
If Err Then
    blokken.Show
    Exit Sub
    End If
Update
End Sub
Sub blok81(pbeginzero)
blokken.Hide
On Error Resume Next
Call Schaal(scaal)
Dim bestand As String
bestand = "C:\acad2002\dwg\goedkeuring.dwg"
Set blockRefObj = ThisDrawing.ModelSpace.InsertBlock(pbeginzero, bestand, scaal, scaal, 1, 0)
If Err Then
    blokken.Show
    Exit Sub
    End If
Update
End Sub
Sub blok91(pbeginzero)
blokken.Hide
On Error Resume Next
Call Schaal(scaal)
Dim bestand As String
bestand = "C:\acad2002\dwg\voorlopig.dwg"
Set blockRefObj = ThisDrawing.ModelSpace.InsertBlock(pbeginzero, bestand, scaal, scaal, 1, 0)
If Err Then
    blokken.Show
    Exit Sub
    End If
Update
End Sub
Sub blok101(pbeginzero)
blokken.Hide
On Error Resume Next
Call Schaal(scaal)
Dim bestand As String
bestand = "C:\acad2002\dwg\allesnaregelen.dwg"
Set blockRefObj = ThisDrawing.ModelSpace.InsertBlock(pbeginzero, bestand, scaal, scaal, 1, 0)
If Err Then
    blokken.Show
    Exit Sub
    End If
Update
End Sub
Sub blok121(pbeginzero)
blokken.Hide
On Error Resume Next
Call Schaal(scaal)
Dim bestand As String
bestand = "C:\acad2002\dwg\uitvoering.dwg"
Set blockRefObj = ThisDrawing.ModelSpace.InsertBlock(pbeginzero, bestand, scaal, scaal, 1, 0)
If Err Then
    blokken.Show
    Exit Sub
    End If
Update
End Sub
Sub blok131(pbeginzero)
blokken.Hide
On Error Resume Next
Call Schaal(scaal)
Dim bestand As String
bestand = "C:\acad2002\dwg\bl-recht.dwg"
Set blockRefObj = ThisDrawing.ModelSpace.InsertBlock(pbeginzero, bestand, scaal, scaal, 1, 0)
If Err Then
    blokken.Show
    Exit Sub
    End If
Update
End Sub
Sub blok1000()
blokken.Hide
On Error Resume Next
Call Schaal(scaal)
Dim pbegin7 As Variant
pbegin7 = ThisDrawing.Utility.GetPoint(, "Plaats het blok -Dilatatie [mantelbuis toepassen]")
Dim bestand As String
bestand = "C:\acad2002\dwg\dilatati.dwg"
Set blockRefObj = ThisDrawing.ModelSpace.InsertBlock(pbegin7, bestand, scaal, scaal, 1, 0)
If Err Then
    blokken.Show
    Exit Sub
    End If
Update
End Sub
Sub blok1100()
blokken.Hide
On Error Resume Next
Call Schaal(scaal)
Dim pbegin7 As Variant
pbegin7 = ThisDrawing.Utility.GetPoint(, "Plaats het blok -Duoleiding- ")
Dim bestand As String
bestand = "C:\acad2002\dwg\bl-duo.dwg"
Set blockRefObj = ThisDrawing.ModelSpace.InsertBlock(pbegin7, bestand, scaal, scaal, 1, 0)
If Err Then
    blokken.Show
    Exit Sub
    End If
Update
End Sub
Sub blok1200()
blokken.Hide
On Error Resume Next
Call Schaal(scaal)
If blok110.Value = True And blok120.Value = True Then ThisDrawing.SetVariable "osmode", 1
Dim pbegin7 As Variant
pbegin7 = ThisDrawing.Utility.GetPoint(, "Plaats het blok -H.O.H. 10 cm- ")
Dim bestand As String
bestand = "C:\acad2002\dwg\bl-hoh10.dwg"
Set blockRefObj = ThisDrawing.ModelSpace.InsertBlock(pbegin7, bestand, scaal, scaal, 1, 0)
If blok110.Value = True And blok120.Value = True Then ThisDrawing.SetVariable "osmode", 0

If Err Then
    ThisDrawing.SetVariable "osmode", 0
    blokken.Show
    Exit Sub
    End If
Update
End Sub
Sub blok1300()
blokken.Hide
On Error Resume Next
Call Schaal(scaal)
Dim pbegin7 As Variant
pbegin7 = ThisDrawing.Utility.GetPoint(, "Plaats het blok -Nivoverschil- ")
Dim bestand As String
bestand = "C:\acad2002\dwg\bl-nivo.dwg"
Set blockRefObj = ThisDrawing.ModelSpace.InsertBlock(pbegin7, bestand, scaal, scaal, 1, 0)
If Err Then
    blokken.Show
    Exit Sub
    End If
Update
End Sub
Sub blok1400()
blokken.Hide
On Error Resume Next
Call Schaal(scaal)
Dim pbegin7 As Variant
pbegin7 = ThisDrawing.Utility.GetPoint(, "Plaats het blok -schetstekening- ")
Dim bestand As String
bestand = "C:\acad2002\dwg\schets.dwg"
Set blockRefObj = ThisDrawing.ModelSpace.InsertBlock(pbegin7, bestand, scaal, scaal, 1, 0)
If Err Then
    blokken.Show
    Exit Sub
    End If
Update
End Sub
Sub blok1500()
blokken.Hide
On Error Resume Next
Call Schaal(scaal)
Dim pbegin7 As Variant
pbegin7 = ThisDrawing.Utility.GetPoint(, "Plaats het blok -wandverwarming 2 meter hoog- ")
Dim bestand As String
bestand = "C:\acad2002\dwg\wand1.dwg"
Set blockRefObj = ThisDrawing.ModelSpace.InsertBlock(pbegin7, bestand, scaal, scaal, 1, 0)
If Err Then
    blokken.Show
    Exit Sub
    End If
Update
End Sub
Sub blok1600()
blokken.Hide
On Error Resume Next
Call Schaal(scaal)
Dim pbegin7 As Variant
pbegin7 = ThisDrawing.Utility.GetPoint(, "Plaats het blok -wandverwarming 2,5 meter hoog- ")
Dim bestand As String
bestand = "C:\acad2002\dwg\wand2.dwg"
Set blockRefObj = ThisDrawing.ModelSpace.InsertBlock(pbegin7, bestand, scaal, scaal, 1, 0)
If Err Then
    blokken.Show
    Exit Sub
    End If
Update
End Sub
Sub blok1700()
blokken.Hide
On Error Resume Next
Call Schaal(scaal)
Dim pbegin7 As Variant
pbegin7 = ThisDrawing.Utility.GetPoint(, "Plaats het blok -Vriescel (Kruispatroon)- ")
Dim bestand As String
bestand = "C:\acad2002\dwg\vriescel1.dwg"
Set blockRefObj = ThisDrawing.ModelSpace.InsertBlock(pbegin7, bestand, scaal, scaal, 1, 0)
If Err Then
    blokken.Show
    Exit Sub
    End If
Update
End Sub
Sub blok1800()
blokken.Hide
On Error Resume Next
Call Schaal(scaal)
Dim bestand As String
bestand = "C:\acad2002\dwg\vriescel2.dwg"
Dim pbegin7 As Variant
pbegin7 = ThisDrawing.Utility.GetPoint(, "Plaats het blok -Vriescel (volgens opritprincipe)- ")
Set blockRefObj = ThisDrawing.ModelSpace.InsertBlock(pbegin7, bestand, scaal, scaal, 1, 0)
If Err Then
    blokken.Show
    Exit Sub
    End If
Update
End Sub
Sub blok1900()
blokken.Hide
On Error Resume Next
Call Schaal(scaal)
Dim pbegin7 As Variant
pbegin7 = ThisDrawing.Utility.GetPoint(, "Plaats het blok -Mantelbuis toepassen- ")
Dim bestand As String
bestand = "C:\acad2002\dwg\mantel.dwg"
Set blockRefObj = ThisDrawing.ModelSpace.InsertBlock(pbegin7, bestand, scaal, scaal, 1, 0)
If Err Then
    blokken.Show
    Exit Sub
    End If
Update
End Sub
Sub optie1()
On Error Resume Next
For Each element In ThisDrawing.ModelSpace
    If element.ObjectName = "AcDbBlockReference" Then
      If element.Name = "bltekor" Or element.Name = "avbltekor" Then
        Set symbool = element
            If symbool.HasAttributes Then
            attributen = symbool.GetAttributes
            For I = LBound(attributen) To UBound(attributen)
            Set attribuut = attributen(I)
            If TextBox1 <> "" Then w1 = TextBox1 & " Watt" & " " & TextBox10 & " " & ComboBox1
            If OptionButton10.Value = True Then w1 = ComboBox1
            If attribuut.TagString = "RUIMTE(N)" And attribuut.textstring = "" Then attribuut.textstring = w1
            Next I
            End If
        End If
    End If
  Next element


If Err Then
    blokken.Show
    Exit Sub
End If
Update
'blok.Show
End Sub
Sub optie2()
For Each element In ThisDrawing.ModelSpace
      If element.ObjectName = "AcDbBlockReference" Then
        If element.Name = "bltekor1" Or element.Name = "avbltekor1" Then
        Set symbool = element
            If symbool.HasAttributes Then
            attributen = symbool.GetAttributes
            For I = LBound(attributen) To UBound(attributen)
            Set attribuut = attributen(I)
            If TextBox1 <> "" Then w1 = TextBox1 & " Watt" & " " & TextBox10 & " " & ComboBox1
            If TextBox2 <> "" Then w2 = TextBox2 & " Watt" & " " & TextBox11 & " " & ComboBox2
            If TextBox3 <> "" Then w3 = TextBox3 & " Watt" & " " & TextBox12 & " " & ComboBox3
            If OptionButton10.Value = True Then
            w1 = ComboBox1
            w2 = ComboBox2
            w3 = ComboBox3
            End If
            If attribuut.TagString = "RUIMTE1" And attribuut.textstring = "" Then attribuut.textstring = w1
            If attribuut.TagString = "RUIMTE2" And attribuut.textstring = "" Then attribuut.textstring = w2
            If attribuut.TagString = "RUIMTE3" And attribuut.textstring = "" Then attribuut.textstring = w3
            Next I
            End If
        End If
      End If
Next element
Update
blok.Show
End Sub
Sub optie3()
For Each element In ThisDrawing.ModelSpace
    If element.ObjectName = "AcDbBlockReference" Then
        If element.Name = "bltekor2" Or element.Name = "avbltekor2" Then
        Set symbool = element
            If symbool.HasAttributes Then
            attributen = symbool.GetAttributes
            For I = LBound(attributen) To UBound(attributen)
            Set attribuut = attributen(I)
            If TextBox1 <> "" Then w1 = TextBox1 & " Watt" & " " & TextBox10 & " " & ComboBox1
            If TextBox2 <> "" Then w2 = TextBox2 & " Watt" & " " & TextBox11 & " " & ComboBox2
            If TextBox3 <> "" Then w3 = TextBox3 & " Watt" & " " & TextBox12 & " " & ComboBox3
            If TextBox4 <> "" Then w4 = TextBox4 & " Watt" & " " & TextBox13 & " " & ComboBox4
            If TextBox5 <> "" Then w5 = TextBox5 & " Watt" & " " & TextBox14 & " " & ComboBox5
            If TextBox6 <> "" Then w6 = TextBox6 & " Watt" & " " & TextBox15 & " " & ComboBox6
            If OptionButton10.Value = True Then
            w1 = ComboBox1
            w2 = ComboBox2
            w3 = ComboBox3
            w4 = ComboBox4
            w5 = ComboBox5
            w6 = ComboBox6
            End If
            If attribuut.TagString = "RUIMTE1" And attribuut.textstring = "" Then attribuut.textstring = w1
            If attribuut.TagString = "RUIMTE2" And attribuut.textstring = "" Then attribuut.textstring = w2
            If attribuut.TagString = "RUIMTE3" And attribuut.textstring = "" Then attribuut.textstring = w3
            If attribuut.TagString = "RUIMTE4" And attribuut.textstring = "" Then attribuut.textstring = w4
            If attribuut.TagString = "RUIMTE5" And attribuut.textstring = "" Then attribuut.textstring = w5
            If attribuut.TagString = "RUIMTE6" And attribuut.textstring = "" Then attribuut.textstring = w6
            Next I
            End If
        End If
    End If
Next element
Update
blok.Show
End Sub
Sub optie4()
For Each element In ThisDrawing.ModelSpace
    If element.ObjectName = "AcDbBlockReference" Then
        If element.Name = "bltekor3" Or element.Name = "avbltekor3" Then
        Set symbool = element
            If symbool.HasAttributes Then
            attributen = symbool.GetAttributes
            For I = LBound(attributen) To UBound(attributen)
            Set attribuut = attributen(I)
            If TextBox1 <> "" Then w1 = TextBox1 & " Watt" & " " & TextBox10 & " " & ComboBox1
            If TextBox2 <> "" Then w2 = TextBox2 & " Watt" & " " & TextBox11 & " " & ComboBox2
            If TextBox3 <> "" Then w3 = TextBox3 & " Watt" & " " & TextBox12 & " " & ComboBox3
            If TextBox4 <> "" Then w4 = TextBox4 & " Watt" & " " & TextBox13 & " " & ComboBox4
            If TextBox5 <> "" Then w5 = TextBox5 & " Watt" & " " & TextBox14 & " " & ComboBox5
            If TextBox6 <> "" Then w6 = TextBox6 & " Watt" & " " & TextBox15 & " " & ComboBox6
            If TextBox7 <> "" Then w7 = TextBox7 & " Watt" & " " & TextBox16 & " " & ComboBox7
            If TextBox8 <> "" Then w8 = TextBox8 & " Watt" & " " & TextBox17 & " " & ComboBox8
            If TextBox9 <> "" Then w9 = TextBox9 & " Watt" & " " & TextBox18 & " " & ComboBox9
            If OptionButton10.Value = True Then
            w1 = ComboBox1
            w2 = ComboBox2
            w3 = ComboBox3
            w4 = ComboBox4
            w5 = ComboBox5
            w6 = ComboBox6
            w7 = ComboBox7
            w8 = ComboBox8
            w9 = ComboBox9
            End If
            If attribuut.TagString = "RUIMTE1" And attribuut.textstring = "" Then attribuut.textstring = w1
            If attribuut.TagString = "RUIMTE2" And attribuut.textstring = "" Then attribuut.textstring = w2
            If attribuut.TagString = "RUIMTE3" And attribuut.textstring = "" Then attribuut.textstring = w3
            If attribuut.TagString = "RUIMTE4" And attribuut.textstring = "" Then attribuut.textstring = w4
            If attribuut.TagString = "RUIMTE5" And attribuut.textstring = "" Then attribuut.textstring = w5
            If attribuut.TagString = "RUIMTE6" And attribuut.textstring = "" Then attribuut.textstring = w6
            If attribuut.TagString = "RUIMTE7" And attribuut.textstring = "" Then attribuut.textstring = w7
            If attribuut.TagString = "RUIMTE8" And attribuut.textstring = "" Then attribuut.textstring = w8
            If attribuut.TagString = "RUIMTE9" And attribuut.textstring = "" Then attribuut.textstring = w9
            Next I
        End If
      End If
    End If
Next element
Update
blok.Show
End Sub
Private Sub ComboBox1_Change()
If ComboBox1.Text = "Kantoor" Or ComboBox1.Text = "Toilet" Or _
ComboBox1.Text = "Zwembad" Or ComboBox1.Text = "Portaal" Or _
ComboBox1.Text = "Bureel" Then
  TextBox10.Value = "in het"
Else
  TextBox10.Value = "in de"
End If
If ComboBox1.Text = "Kantoor1" Or ComboBox1.Text = "Kantoor2" Or _
ComboBox1.Text = "Verblijfsruimte1" Or ComboBox1.Text = "Verblijfsruimte2" Or _
ComboBox1.Text = "Groepsruimte1" Or ComboBox1.Text = "Groepsruimte2" Or _
ComboBox1.Text = "Slaapkamer1" Or ComboBox1.Text = "Slaapkamer2" Or _
ComboBox1.Text = "Slaapkamer3" Or ComboBox1.Text = "Slaapkamer4" Or _
ComboBox1.Text = "Bedrijfsruimte1" Or ComboBox1.Text = "Bedrijfsruimte2" Then
  TextBox10.Value = "in"
End If
If ComboBox1.Text = "Verkoop" Or ComboBox1.Text = "Zolder" Or ComboBox1.Text = "Overloop" Then
  TextBox10.Value = "op de"
End If
If ComboBox1.Text = "" Then
  TextBox10.Value = Clear
  TextBox10.Locked = True
Else
  TextBox10.Locked = False
  End If
  
End Sub
Private Sub ComboBox2_Change()

If ComboBox2.Text = "Kantoor" Or ComboBox2.Text = "Toilet" Or _
ComboBox2.Text = "Zwembad" Or ComboBox2.Text = "Portaal" Or _
ComboBox2.Text = "Bureel" Then
  TextBox11.Value = "in het"
 Else
  TextBox11.Value = "in de"
End If
If ComboBox2.Text = "Kantoor1" Or ComboBox2.Text = "Kantoor2" Or _
ComboBox2.Text = "Verblijfsruimte1" Or ComboBox2.Text = "Verblijfsruimte2" Or _
ComboBox2.Text = "Groepsruimte1" Or ComboBox2.Text = "Groepsruimte2" Or _
ComboBox2.Text = "Slaapkamer1" Or ComboBox2.Text = "Slaapkamer2" Or _
ComboBox2.Text = "Slaapkamer3" Or ComboBox2.Text = "Slaapkamer4" Or _
ComboBox2.Text = "Bedrijfsruimte1" Or ComboBox2.Text = "Bedrijfsruimte2" Then
  TextBox11.Value = "in"
End If
If ComboBox2.Text = "Verkoop" Or ComboBox2.Text = "Zolder" Or ComboBox2.Text = "Overloop" Then
  TextBox11.Value = "op de"
End If
If ComboBox2.Text = "" Then
  TextBox11.Value = Clear
  TextBox11.Locked = True
Else
  TextBox11.Locked = False
  End If

End Sub
Private Sub ComboBox3_Change()

If ComboBox3.Text = "Kantoor" Or ComboBox3.Text = "Toilet" Or _
ComboBox3.Text = "Zwembad" Or ComboBox3.Text = "Portaal" Or _
ComboBox3.Text = "Bureel" Then
 TextBox12.Value = "in het"
 Else
  TextBox12.Value = "in de"
End If
If ComboBox3.Text = "Kantoor1" Or ComboBox3.Text = "Kantoor2" Or _
ComboBox3.Text = "Verblijfsruimte1" Or ComboBox3.Text = "Verblijfsruimte2" Or _
ComboBox3.Text = "Groepsruimte1" Or ComboBox3.Text = "Groepsruimte2" Or _
ComboBox3.Text = "Slaapkamer1" Or ComboBox3.Text = "Slaapkamer2" Or _
ComboBox3.Text = "Slaapkamer3" Or ComboBox3.Text = "Slaapkamer4" Or _
ComboBox3.Text = "Bedrijfsruimte1" Or ComboBox3.Text = "Bedrijfsruimte2" Then
  TextBox12.Value = "in"
End If
If ComboBox3.Text = "Verkoop" Or ComboBox3.Text = "Zolder" Or ComboBox3.Text = "Overloop" Then
  TextBox12.Value = "op de"
End If
If ComboBox3.Text = "" Then
  TextBox12.Value = Clear
  TextBox12.Locked = True
Else
  TextBox12.Locked = False
  End If
End Sub
Private Sub Combobox4_Change()

If ComboBox4.Text = "Kantoor" Or ComboBox4.Text = "Toilet" Or _
ComboBox4.Text = "Zwembad" Or ComboBox4.Text = "Portaal" Or _
ComboBox4.Text = "Bureel" Then
 TextBox13.Value = "in het"
 Else
  TextBox13.Value = "in de"
End If
If ComboBox4.Text = "Kantoor1" Or ComboBox4.Text = "Kantoor2" Or _
ComboBox4.Text = "Verblijfsruimte1" Or ComboBox4.Text = "Verblijfsruimte2" Or _
ComboBox4.Text = "Groepsruimte1" Or ComboBox4.Text = "Groepsruimte2" Or _
ComboBox4.Text = "Slaapkamer1" Or ComboBox4.Text = "Slaapkamer2" Or _
ComboBox4.Text = "Slaapkamer3" Or ComboBox4.Text = "Slaapkamer4" Or _
ComboBox4.Text = "Bedrijfsruimte1" Or ComboBox4.Text = "Bedrijfsruimte2" Then
  TextBox13.Value = "in"
End If
If ComboBox4.Text = "Verkoop" Or ComboBox4.Text = "Zolder" Or ComboBox4.Text = "Overloop" Then
  TextBox13.Value = "op de"
End If
If ComboBox4.Text = "" Then
  TextBox13.Value = Clear
  TextBox13.Locked = True
Else
  TextBox13.Locked = False
  End If

End Sub


Private Sub Combobox5_Change()

If ComboBox5.Text = "Kantoor" Or ComboBox5.Text = "Toilet" Or _
ComboBox5.Text = "Zwembad" Or ComboBox5.Text = "Portaal" Or _
ComboBox5.Text = "Bureel" Then
 TextBox14.Value = "in het"
 Else
  TextBox14.Value = "in de"
End If
If ComboBox5.Text = "Kantoor1" Or ComboBox5.Text = "Kantoor2" Or _
ComboBox5.Text = "Verblijfsruimte1" Or ComboBox5.Text = "Verblijfsruimte2" Or _
ComboBox5.Text = "Groepsruimte1" Or ComboBox5.Text = "Groepsruimte2" Or _
ComboBox5.Text = "Slaapkamer1" Or ComboBox5.Text = "Slaapkamer2" Or _
ComboBox5.Text = "Slaapkamer3" Or ComboBox5.Text = "Slaapkamer4" Or _
ComboBox5.Text = "Bedrijfsruimte1" Or ComboBox5.Text = "Bedrijfsruimte2" Then
  TextBox14.Value = "in"
End If
If ComboBox5.Text = "Verkoop" Or ComboBox5.Text = "Zolder" Or ComboBox5.Text = "Overloop" Then
  TextBox14.Value = "op de"
End If
If ComboBox5.Text = "" Then
  TextBox14.Value = Clear
  TextBox14.Locked = True
Else
  TextBox14.Locked = False
  End If

End Sub
Private Sub Combobox6_Change()

If ComboBox6.Text = "Kantoor" Or ComboBox6.Text = "Toilet" Or _
ComboBox6.Text = "Zwembad" Or ComboBox6.Text = "Portaal" Or _
ComboBox6.Text = "Bureel" Then
 TextBox15.Value = "in het"
 Else
  TextBox15.Value = "in de"
End If
If ComboBox6.Text = "Kantoor1" Or ComboBox6.Text = "Kantoor2" Or _
ComboBox6.Text = "Verblijfsruimte1" Or ComboBox6.Text = "Verblijfsruimte2" Or _
ComboBox6.Text = "Groepsruimte1" Or ComboBox6.Text = "Groepsruimte2" Or _
ComboBox6.Text = "Slaapkamer1" Or ComboBox6.Text = "Slaapkamer2" Or _
ComboBox6.Text = "Slaapkamer3" Or ComboBox6.Text = "Slaapkamer4" Or _
ComboBox6.Text = "Bedrijfsruimte1" Or ComboBox6.Text = "Bedrijfsruimte2" Then
  TextBox15.Value = "in"
End If
If ComboBox6.Text = "Verkoop" Or ComboBox6.Text = "Zolder" Or ComboBox6.Text = "Overloop" Then
  TextBox15.Value = "op de"
End If
If ComboBox6.Text = "" Then
  TextBox15.Value = Clear
  TextBox15.Locked = True
Else
  TextBox15.Locked = False
  End If

End Sub
Private Sub Combobox7_Change()

If ComboBox7.Text = "Kantoor" Or ComboBox7.Text = "Toilet" Or _
ComboBox7.Text = "Zwembad" Or ComboBox7.Text = "Portaal" Or _
ComboBox7.Text = "Bureel" Then
 TextBox16.Value = "in het"
 Else
  TextBox16.Value = "in de"
End If
If ComboBox7.Text = "Kantoor1" Or ComboBox7.Text = "Kantoor2" Or _
ComboBox7.Text = "Verblijfsruimte1" Or ComboBox7.Text = "Verblijfsruimte2" Or _
ComboBox7.Text = "Groepsruimte1" Or ComboBox7.Text = "Groepsruimte2" Or _
ComboBox7.Text = "Slaapkamer1" Or ComboBox7.Text = "Slaapkamer2" Or _
ComboBox7.Text = "Slaapkamer3" Or ComboBox7.Text = "Slaapkamer4" Or _
ComboBox7.Text = "Bedrijfsruimte1" Or ComboBox7.Text = "Bedrijfsruimte2" Then
  TextBox16.Value = "in"
End If
If ComboBox7.Text = "Verkoop" Or ComboBox7.Text = "Zolder" Or ComboBox7.Text = "Overloop" Then
  TextBox16.Value = "op de"
End If
If ComboBox7.Text = "" Then
  TextBox16.Value = Clear
  TextBox16.Locked = True
Else
  TextBox16.Locked = False
  End If

End Sub
Private Sub Combobox8_Change()

If ComboBox8.Text = "Kantoor" Or ComboBox8.Text = "Toilet" Or _
ComboBox8.Text = "Zwembad" Or ComboBox8.Text = "Portaal" Or _
ComboBox8.Text = "Bureel" Then
 TextBox17.Value = "in het"
 Else
  TextBox17.Value = "in de"
End If
If ComboBox8.Text = "Kantoor1" Or ComboBox8.Text = "Kantoor2" Or _
ComboBox8.Text = "Verblijfsruimte1" Or ComboBox8.Text = "Verblijfsruimte2" Or _
ComboBox8.Text = "Groepsruimte1" Or ComboBox8.Text = "Groepsruimte2" Or _
ComboBox8.Text = "Slaapkamer1" Or ComboBox8.Text = "Slaapkamer2" Or _
ComboBox8.Text = "Slaapkamer3" Or ComboBox8.Text = "Slaapkamer4" Or _
ComboBox8.Text = "Bedrijfsruimte1" Or ComboBox8.Text = "Bedrijfsruimte2" Then
  TextBox17.Value = "in"
End If
If ComboBox8.Text = "Verkoop" Or ComboBox8.Text = "Zolder" Or ComboBox8.Text = "Overloop" Then
  TextBox17.Value = "op de"
End If
If ComboBox8.Text = "" Then
  TextBox17.Value = Clear
  TextBox17.Locked = True
Else
  TextBox17.Locked = False
  End If

End Sub
Private Sub Combobox9_Change()
If ComboBox9.Text = "Kantoor" Or ComboBox9.Text = "Toilet" Or _
ComboBox9.Text = "Zwembad" Or ComboBox9.Text = "Portaal" Or _
ComboBox9.Text = "Bureel" Then
 TextBox18.Value = "in het"
 Else
  TextBox18.Value = "in de"
End If
If ComboBox9.Text = "Kantoor1" Or ComboBox9.Text = "Kantoor2" Or _
ComboBox9.Text = "Verblijfsruimte1" Or ComboBox9.Text = "Verblijfsruimte2" Or _
ComboBox9.Text = "Groepsruimte1" Or ComboBox9.Text = "Groepsruimte2" Or _
ComboBox9.Text = "Slaapkamer1" Or ComboBox9.Text = "Slaapkamer2" Or _
ComboBox9.Text = "Slaapkamer3" Or ComboBox9.Text = "Slaapkamer4" Or _
ComboBox9.Text = "Bedrijfsruimte1" Or ComboBox9.Text = "Bedrijfsruimte2" Then
  TextBox18.Value = "in"
End If
If ComboBox9.Text = "Verkoop" Or ComboBox9.Text = "Zolder" Or ComboBox9.Text = "Overloop" Then
  TextBox18.Value = "op de"
End If
If ComboBox9.Text = "" Then
  TextBox18.Value = Clear
  TextBox18.Locked = True
Else
  TextBox18.Locked = False
  End If
End Sub
Sub Schaal(scaal)
blokken.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
Update
End Sub

Attribute VB_Name = "frmBouwnummer"
Attribute VB_Base = "0{0A4B664B-C9E4-43FA-99BB-CCF6BE6930B1}{2DA8B908-11EB-415E-8BA3-1ED48D7AE1F7}"
Attribute VB_GlobalNameSpace = False
Attribute VB_Creatable = False
Attribute VB_PredeclaredId = True
Attribute VB_Exposed = False
Attribute VB_TemplateDerived = False
Attribute VB_Customizable = False

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000

Private Sub UserForm_Initialize()
'begin sluiten toets uitschakelen
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
'einde sluiten toets uitschakelen
frmBouwnummer.TextBox3.SetFocus
End Sub
Private Sub CancelButton_Click()
If frmBouwnummer.TextBox3 <> "" Then blokken.TextBox21 = "BOUWNUMMER: " & frmBouwnummer.TextBox3 'bouwnummer
If frmBouwnummer.TextBox2 <> "" Then blokken.TextBox22 = "TYPE: " & frmBouwnummer.TextBox2 'type
If TextBox3 = "" And TextBox2 = "" Then blokken.CheckBox2 = False
Unload Me
blokken.Show
End Sub
Private Sub CommandButton1_Click()
frmBouwnummer.TextBox2 = Clear: frmBouwnummer.TextBox3 = Clear
frmBouwnummer.TextBox3.SetFocus
End Sub

Attribute VB_Name = "frmDrawingcheck"
Attribute VB_Base = "0{E0DB1CE3-7006-4B2A-91AE-D4ADD1CB88F5}{D8B868F0-51DA-4F2B-94D9-5C4C43FA3877}"
Attribute VB_GlobalNameSpace = False
Attribute VB_Creatable = False
Attribute VB_PredeclaredId = True
Attribute VB_Exposed = False
Attribute VB_TemplateDerived = False
Attribute VB_Customizable = False

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000


Private Sub UserForm_Initialize()
'begin sluiten toets uitschakelen
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
End Sub
Private Sub cmdAfsluiten_Click()
Unload Me
End Sub

Private Sub go_Click()
Dim element500 As Object
AZ = 0
For Each element500 In ThisDrawing.ModelSpace
      If element500.ObjectName = "AcDbBlockReference" Then
         If UCase(element500.Name) = "MAT_SPE_ZD" Or UCase(element500.Name) = "MAT_SPE_PE" _
         Or UCase(element500.Name) = "MAT_SPE_ZD_1627" Or UCase(element500.Name) = "MAT_SPE_PE800" Then AZ = AZ + 1
      End If
Next element500
On Error Resume Next

For I = 1 To AZ

Dim j As String
j = I
If j > 0 And j < 10 Then k = "0" & j
If j > 9 Then k = j

Dim TRIMSTRING
For Each element2 In ThisDrawing.ModelSpace
      If element2.ObjectName = "AcDbBlockReference" Then
      If UCase(element2.Name) = "MAT_SPE_ZD" Or UCase(element2.Name) = "MAT_SPE_PE" _
      Or UCase(element2.Name) = "MAT_SPE_ZD_1627" Or UCase(element2.Name) = "MAT_SPE_PE800" Then
      Set symbool = element2
        If symbool.HasAttributes Then
        attributen = symbool.GetAttributes
        For O = LBound(attributen) To UBound(attributen)
         Set attribuut = attributen(O)
               If attribuut.TagString = "RNU" Then
                   hk = attribuut.textstring
                   If hk = k Then
                        b0 = element2.InsertionPoint
                        c0 = b0
                        For y = LBound(attributen) To UBound(attributen)
                           Set attribuut = attributen(y)
                             If hk = k Then
                              If attribuut.TagString = "REGELUNITTYPE" Then
                              RT = attribuut.textstring
                     
                               TRIMSTRING = Split(RT, (" "))
                               mystr = Len(TRIMSTRING(1))
                                   If mystr > 2 Then
                                   trimstring2 = Split(TRIMSTRING(1), ("/"))
                                   TextBox1 = trimstring2(0)
                                   Else
                                   TextBox1 = TRIMSTRING(1)
                                   End If
                              End If
                             End If
                             
    'aanvulling under construction--------------------------------------------------------------
             If attribuut.TagString = "WTH250" And attribuut.textstring <> "-" Then
             yt = attribuut.textstring
             TextBox4 = Val(TextBox4) + yt * 250
             End If
             If attribuut.TagString = "WTH165" And attribuut.textstring <> "-" Then
             yt = attribuut.textstring
             TextBox4 = Val(TextBox4) + yt * 165
             End If
             If attribuut.TagString = "WTH125" And attribuut.textstring <> "-" Then
             yt = attribuut.textstring
             TextBox4 = Val(TextBox4) + yt * 125
             End If
             If attribuut.TagString = "WTH105" And attribuut.textstring <> "-" Then
             yt = attribuut.textstring
             TextBox4 = Val(TextBox4) + yt * 105
             End If
             If attribuut.TagString = "WTH90" And attribuut.textstring <> "-" Then
             yt = attribuut.textstring
             TextBox4 = Val(TextBox4) + yt * 90
             End If
             If attribuut.TagString = "WTH75" And attribuut.textstring <> "-" Then
             yt = attribuut.textstring
             TextBox4 = Val(TextBox4) + yt * 75
             End If
             If attribuut.TagString = "WTH63" And attribuut.textstring <> "-" Then
             yt = attribuut.textstring
             TextBox4 = Val(TextBox4) + yt * 63
             End If
             If attribuut.TagString = "WTH50" And attribuut.textstring <> "-" Then
             yt = attribuut.textstring
             TextBox4 = Val(TextBox4) + yt * 50
             End If
             If attribuut.TagString = "WTH40" And attribuut.textstring <> "-" Then
             yt = attribuut.textstring
             TextBox4 = Val(TextBox4) + yt * 40
             End If
             
             ' pe-rt 120,90,60
             If attribuut.TagString = "PE120" And attribuut.textstring <> "-" Then
             yt = attribuut.textstring
             TextBox4 = Val(TextBox4) + yt * 120
             End If
             If attribuut.TagString = "PE90" And attribuut.textstring <> "-" Then
             yt = attribuut.textstring
             TextBox4 = Val(TextBox4) + yt * 90
             End If
             If attribuut.TagString = "PE60" And attribuut.textstring <> "-" Then
             yt = attribuut.textstring
             TextBox4 = Val(TextBox4) + yt * 60
             End If
       'aanvulling under construction--------------------------------------------------------------
                       Next y
                   End If
               End If
       Next O
       
      End If
      End If
      End If
 Next element2
     


For Each element In ThisDrawing.ModelSpace
        If element.ObjectName = "AcDbBlockReference" Then
            If UCase(element.Name) = "GROEPTEKSTBLOKNEW" Then
                Set symbool = element
                If symbool.HasAttributes Then
                    attributen = symbool.GetAttributes
                    For m = LBound(attributen) To UBound(attributen)
                         Set attribuut = attributen(m)
                         If attribuut.TagString = "UNITNUMMER" Then
                            GH = attribuut.textstring
                            If GH = k Then
                             For z = LBound(attributen) To UBound(attributen)
                               Set attribuut = attributen(z)
                               If GH = k Then
                                If attribuut.TagString = "ROLLENGTE" And attribuut.textstring <> " " Then
                                TextBox2 = TextBox2 + 1
                                qwer = Split(attribuut.textstring)
                                TextBox3 = Val(TextBox3) + qwer(0)
                                End If
                               End If
                             Next z
                            End If
                         End If
                    Next m
                End If
            End If
        End If

    Next element



If TextBox1 <> TextBox2 Then
   MsgBox "Het totaal aantal groepen in het unit bloklogo" & (Chr(13) & Chr(10)) & _
          "en het totaal aantal groeptekstblokken" & (Chr(13) & Chr(10)) & _
          "van " & "UNIT: " & k & " wijken af.", vbExclamation
          
  Dim b1(0 To 2) As Double
  b1(0) = b0(0) - 1500 '1000
  b1(1) = b0(1) - 400  '500
  b1(2) = 0
 
  Dim b2(0 To 2) As Double
  b2(0) = b0(0) + 500
  b2(1) = b0(1) + 1000 '750
  b2(2) = 0
  ZoomWindow b1, b2
          
          
   Unload Me
   Exit Sub
End If

If TextBox3 <> TextBox4 Then
   MsgBox "Het aantal meters in het unit bloklogo" & (Chr(13) & Chr(10)) & _
          "en het aantal meters van de groeptekstblokken" & (Chr(13) & Chr(10)) & _
          "van " & "UNIT: " & k & " wijken af.", vbCritical
          
  Dim c1(0 To 2) As Double
  c1(0) = c0(0) - 1500 '1000
  c1(1) = c0(1) - 400  '500
  c1(2) = 0
 
  Dim c2(0 To 2) As Double
  c2(0) = c0(0) + 500
  c2(1) = c0(1) + 1000 '750
  c2(2) = 0
  ZoomWindow c1, c2
          
          
   Unload Me
   Exit Sub
End If


If TextBox1 = TextBox2 Then
  TextBox1 = Clear
  TextBox2 = "0"
End If
If TextBox3 = TextBox4 Then
  TextBox3 = "0"
  TextBox4 = "0"
End If



Next I

Unload Me
End Sub

Attribute VB_Name = "frmLayerlijst"
Attribute VB_Base = "0{AB2EEB97-C6AE-479B-B0E0-2EF7161400DF}{D865F318-3F5A-4150-8EB7-204867F620FD}"
Attribute VB_GlobalNameSpace = False
Attribute VB_Creatable = False
Attribute VB_PredeclaredId = True
Attribute VB_Exposed = False
Attribute VB_TemplateDerived = False
Attribute VB_Customizable = False
'26-01-2004 Layerlijst genereren
'M.Bosch en G.C.Haak

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If
Private Const MF_BYPOSITION = &H400
Private Const MF_REMOVE = &H1000

Private Sub CommandButton3_Click()
Unload Me
End Sub

Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If

 On Error Resume Next
 
 frmLayerlijst.Width = 500
 frmLayerlijst.Height = 307
 
 
 Kill ("c:\acad2002\layerlijst.txt")
 ComboBox1.AddItem "2.5"
 ComboBox1.AddItem "2"
 ComboBox1.Text = ComboBox1.List(0)

''''' If TextBox14 > 30 Then Call importuserr2
''''' If TextBox14 < 31 Then TextBox13 = ThisDrawing.GetVariable("USERR2")
 End Sub
Private Sub CheckBox5_Click()
If ListBox1.ListCount = 0 Then TextBox12 = 0
 
If CheckBox5.Value = True Then
Frame1.Visible = True
Label24.Visible = False
TextBox12.Visible = False
frmLayerlijst.Width = 488
TextBox20 = TextBox12
'TextBox25 = Val(TextBox25) * (Val(TextBox2) + Val(TextBox3) + Val(TextBox4))
TextBox25 = 0
TextBox26 = TextBox12
Else
'frmLayerlijst.Width = 352
Label24.Visible = True
TextBox12.Visible = True
Frame1.Visible = False
frmLayerlijst.Width = 488
End If
End Sub
Private Sub TextBox21_Change()
On Error Resume Next
Dim b As Double
b = TextBox21.Text
  If Err Then
   If TextBox21 = "" Then TextBox21 = 0
  Exit Sub
  End If

TextBox26 = Val(TextBox26) - (800 * Val(TextBox21))

If Label30.Caption = "0" Then Label30 = TextBox21
If TextBox21 = "0" Or TextBox21 = "" Then TextBox26 = Val(TextBox26) + (800 * Val(Label30))
Label30.Caption = TextBox21
End Sub
Private Sub TextBox22_Change()
On Error Resume Next
Dim b As Double
b = TextBox22.Text
  If Err Then
   If TextBox22 = "" Then TextBox22 = 0
  Exit Sub
  End If

TextBox26 = Val(TextBox26) - (120 * Val(TextBox22))

If Label31.Caption = "0" Then Label31 = TextBox22
If TextBox22 = "0" Or TextBox22 = "" Then TextBox26 = Val(TextBox26) + (120 * Val(Label31))
Label31.Caption = TextBox22
End Sub
Private Sub TextBox23_Change()
On Error Resume Next
Dim b As Double
b = TextBox23.Text
  If Err Then
   If TextBox23 = "" Then TextBox23 = 0
  Exit Sub
  End If

TextBox26 = Val(TextBox26) - (90 * Val(TextBox23))

If Label32.Caption = "0" Then Label32 = TextBox23
If TextBox23 = "0" Or TextBox23 = "" Then TextBox26 = Val(TextBox26) + (90 * Val(Label32))
Label32.Caption = TextBox23
End Sub
Private Sub TextBox24_Change()
On Error Resume Next
Dim b As Double
b = TextBox24.Text
  If Err Then
   If TextBox24 = "" Then TextBox24 = 0
  Exit Sub
  End If

TextBox26 = Val(TextBox26) - (60 * Val(TextBox24))

If Label33.Caption = "0" Then Label33 = TextBox24
If TextBox24 = "0" Or TextBox24 = "" Then TextBox26 = Val(TextBox26) + (60 * Val(Label33))
Label33.Caption = TextBox24
End Sub
Private Sub TextBox25_Change()
TextBox26 = (Val(TextBox20)) + (Val(TextBox25) * (Val(TextBox2) + Val(TextBox3) + Val(TextBox4)))
End Sub
Sub exportuserr2()
TT = ThisDrawing.GetVariable("USERR2")
Const ForReading = 1, ForWriting = 2, ForAppending = 8
Dim fg, fh
'Dim s1 As AcadSelectionSet
Set fg = CreateObject("Scripting.FileSystemObject")

Set fh = fg.OpenTextFile("c:\acad2002\userr2.txt", ForWriting, -2)
    fh.write TT
    fh.Close
End Sub
Sub importuserr2()
Const ForReading = 1, ForWriting = 2, ForAppending = 3
Const TristateUseDefault = -2, TristateTrue = -1, TristateFalse = 0
Dim fl, m, TS
Set fl = CreateObject("Scripting.FileSystemObject")
Set m = fl.OpenTextFile("c:\acad2002\userr2.txt", ForReading, False)
    TS = m.ReadLine
    TextBox13 = TS
m.Close 'sluiten van tekstbestand
End Sub
Private Sub CommandButton1_Click()
    'Ensure ListBox contains list items
    If ListBox1.ListCount >= 1 Then
        'If no selection, choose last list item.
        If ListBox1.ListIndex = -1 Then
            ListBox1.ListIndex = _
                    ListBox1.ListCount - 1
        End If
        ListBox1.RemoveItem (ListBox1.ListIndex)
    End If
    Update
ListBox1.AddItem TextBox1.Text
Update

 'lijst rangschikken
  Dim Veld(0 To 500)
  Dim textstring2 As String
  
    For I = 0 To ListBox1.ListCount - 1
    textstring2 = ListBox1.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox1.Clear
 
  For x = 0 To UBound(Veld)
  If Veld(x) <> "" Then ListBox1.AddItem Veld(x)
  Next x

TextBox1 = Clear
CommandButton1.Locked = True
'ListBox1.RemoveItem (laagnaam)
End Sub
Private Sub ListBox1_DblClick(ByVal Cancel As MSForms.ReturnBoolean)
Dim naam As Object
laagnaam = ListBox1.Text
TextBox1 = laagnaam
Update

End Sub

Private Sub OptionButton1_Click()
frmLayerlijst.Height = 422
Cmdprint.Enabled = False
ListBox1.Clear
ListBox2.Clear
frmLayerlijst.Width = 488
Label2 = q250: Label4 = q165: Label6 = q125: Label9 = q105: Label11 = q90: Label12 = q75: Label12 = q63
TextBox5.Visible = True: TextBox6.Visible = True: TextBox7.Visible = True: TextBox8.Visible = True
TextBox9.Visible = True: TextBox10.Visible = True: TextBox11.Visible = True
Label1.Caption = "250 meter": Label3.Caption = "165 meter": Label5.Caption = "125 meter"
Label8.Caption = "105 meter": Label10.Caption = "90 meter": Label7.Caption = "75 meter"
Label13.Caption = "63 meter": Label21.Caption = "50 meter": Label22.Caption = "40 meter"
Label15.Caption = Clear
Label17.Caption = Clear
Label15.BackColor = &HC0C0C0
CheckBox5.Visible = False
Frame1.Visible = False
Label24.Visible = False
TextBox12.Visible = False


    TextBox2 = ""
    TextBox3 = ""
    TextBox4 = ""
    TextBox5 = ""
    TextBox6 = ""
    TextBox7 = ""
    TextBox8 = ""
    TextBox10 = ""
    TextBox11 = ""
End Sub

Private Sub OptionButton2_Click()
Label24.Visible = False
TextBox12.Visible = False
frmLayerlijst.Height = 422
Cmdprint.Enabled = False
ListBox1.Clear
ListBox2.Clear
frmLayerlijst.Width = 488
Label15.Caption = Clear
Label17.Caption = Clear
Label15.BackColor = &HC0C0C0
CheckBox5.Visible = True
CheckBox5.Enabled = True

    TextBox2 = ""
    TextBox3 = ""
    TextBox4 = ""
    TextBox5.Visible = False
    TextBox6.Visible = False
    TextBox7.Visible = False
    TextBox8.Visible = False
    TextBox10.Visible = False
    TextBox11.Visible = False
    Label1.Caption = "120 meter"
    Label3.Caption = "90 meter"
    Label5.Caption = "60 meter"
    Label7.Caption = Clear
    Label8.Caption = Clear
    Label10.Caption = Clear
    Label13.Caption = Clear
    Label21.Caption = Clear
    Label22.Caption = Clear
End Sub
Private Sub TextBox1_Change()
If TextBox1 <> "" Then CommandButton1.Locked = False
End Sub
Private Sub cmdLayers_Click()
'Call Checklayer.Checklayer  'module kijkt of er lege layers zijn
 Call LEIDINGSOORT
 Call extreemtek
 
 
ListBox1.Clear
ListBox2.Clear
Update
On Error Resume Next
  
 Dim cirkel As Object
 Dim element As Object
 Dim Lengte As Double
 Dim laagobj As Object
 
 Dim minaantal As Integer
 Dim maxaantal As Integer
 Dim I As Integer
 I = 0
 minaantal = 0
 maxaantal = ThisDrawing.Layers.Count
 For Each laagobj In ThisDrawing.Layers
 I = I + 1
 ProgressBar1.Min = minaantal
 ProgressBar1.Max = maxaantal
 ProgressBar1.Value = I
 
      mystr = Left(laagobj.Name, 5)
      If mystr = "GROEP" Then mystr = "groep"
      If Not mystr = "groep" Then
      GoTo wand
      Else
        For Each element In ThisDrawing.ModelSpace
          If element.Layer = laagobj.Name Then
                'BEREKENEN TOTALE LENGTE
                If element.EntityName = "AcDbLine" Then Lengte = Lengte + element.Length
                If element.EntityName = "AcDbArc" Then Lengte = Lengte + element.ArcLength
             End If 'elementlayer
             Next element
            
              For Each cirkel In ThisDrawing.ModelSpace
                If cirkel.Layer = laagobj.Name Then
                If cirkel.EntityName = "AcDbCircle" Then
                z = z + 1
                wvaanwezig = " (WV)"
                zlengte = (z * (ComboBox1.Text * 100)) + 100
                End If
                End If
                Next cirkel
                
                
                
                
wand:
        If mystr = "WAND_" Then mystr = "wand_"
        If mystr = "wand_" Then
             For Each element In ThisDrawing.ModelSpace
             If element.Layer = laagobj.Name Then
                'BEREKENEN TOTALE LENGTE
                If element.EntityName = "AcDbLine" Then Lengte = Lengte + element.Length
                If element.EntityName = "AcDbArc" Then Lengte = Lengte + element.ArcLength
                         
             End If 'elementlayer
             Next element
             
                For Each cirkel In ThisDrawing.ModelSpace
                If cirkel.Layer = laagobj.Name Then
                If cirkel.EntityName = "AcDbCircle" Then
                z = z + 1
                wvaanwezig = " (WV)"
                End If
                End If
                Next cirkel
                zlengte = (z * (ComboBox1.Text * 100)) + 100
                End If '2e mystr
                
    Lengte = (Lengte * TextBox19) + zlengte
    'Lengte = Lengte + zlengte
    Lengte = (Lengte / 100) + Val(TextBox27)
    Lengte = Round(Lengte, 1)
    totalrollen = totalrollen + Lengte
    
    'nieuwe tekeningen
    If frmLayerlijst.CheckBox3.Value = False Then
   'WTH-ZD-leiding
    If Lengte >= 162.5 And Lengte < 250 And OptionButton1.Value = True Then
    q250 = q250 + 1
    e = "--> wordt een rol van 250 meter"
    End If
    If Lengte >= 122.5 And Lengte < 162.5 And OptionButton1.Value = True Then
    q165 = q165 + 1
    e = "--> wordt een rol van 165 meter"
    End If
    If Lengte >= 102.5 And Lengte < 122.5 And OptionButton1.Value = True Then
    q125 = q125 + 1
    e = "--> wordt een rol van 125 meter"
    End If
    If Lengte >= 87.5 And Lengte < 102.5 And OptionButton1.Value = True Then
    q105 = q105 + 1
    e = "--> wordt een rol van 105 meter"
    End If
    If Lengte >= 72.5 And Lengte < 87.5 And OptionButton1.Value = True Then
    q90 = q90 + 1
    e = "--> wordt een rol van 90 meter"
    End If
    If Lengte >= 60.5 And Lengte < 72.5 And OptionButton1.Value = True Then
    q75 = q75 + 1
    e = "--> wordt een rol van 75 meter"
    End If
    If Lengte >= 47.5 And Lengte < 60.5 And OptionButton1.Value = True Then
    q63 = q63 + 1
    e = "--> wordt een rol van 63 meter"
    End If
    If Lengte >= 37.5 And Lengte < 47.5 And OptionButton1.Value = True Then
    q50 = q50 + 1
    e = "--> wordt een rol van 50 meter"
    End If
    If Lengte >= 10 And Lengte < 37.5 And OptionButton1.Value = True Then
    q40 = q40 + 1
    e = "--> wordt een rol van 40 meter"
    End If
    
    
    'PE-RT-leiding
    If Lengte >= 87.5 And Lengte < 120 And OptionButton2.Value = True Then
    qpe120 = qpe120 + 1
    e = "--> wordt een rol van 120 meter"
    End If
    If Lengte >= 120 And OptionButton2.Value = True And CheckBox5.Value = True Then
    qpe120 = qpe120 + 1
    e = "--> wordt een rol van 120 meter"
    End If
    If Lengte >= 57.5 And Lengte < 87.5 And OptionButton2.Value = True Then
    qpe90 = qpe90 + 1
    e = "--> wordt een rol van 90 meter"
    End If
    If Lengte >= 10 And Lengte < 57.5 And OptionButton2.Value = True Then
    qpe60 = qpe60 + 1
    e = "--> wordt een rol van 60 meter"
    End If
    End If 'nieuwe tekeningen
  
  'oude tekeningen
    If frmLayerlijst.CheckBox3.Value = True Then
   'WTH-ZD-leiding
    If Lengte >= 163.6 And Lengte < 250 And OptionButton1.Value = True Then
    q250 = q250 + 1
    e = "--> wordt een rol van 250 meter"
    End If
    If Lengte >= 123.6 And Lengte < 163.6 And OptionButton1.Value = True Then
    q165 = q165 + 1
    e = "--> wordt een rol van 165 meter"
    End If
    If Lengte >= 103.6 And Lengte < 123.6 And OptionButton1.Value = True Then
    q125 = q125 + 1
    e = "--> wordt een rol van 125 meter"
    End If
    If Lengte >= 88.6 And Lengte < 103.6 And OptionButton1.Value = True Then
    q105 = q105 + 1
    e = "--> wordt een rol van 105 meter"
    End If
    If Lengte >= 73.6 And Lengte < 88.6 And OptionButton1.Value = True Then
    q90 = q90 + 1
    e = "--> wordt een rol van 90 meter"
    End If
    If Lengte >= 61.6 And Lengte < 73.6 And OptionButton1.Value = True Then
    q75 = q75 + 1
    e = "--> wordt een rol van 75 meter"
    End If
    If Lengte >= 48.6 And Lengte < 61.6 And OptionButton1.Value = True Then
    q63 = q63 + 1
    e = "--> wordt een rol van 63 meter"
    End If
    If Lengte >= 38.6 And Lengte < 48.6 And OptionButton1.Value = True Then
    q50 = q50 + 1
    e = "--> wordt een rol van 50 meter"
    End If
    If Lengte >= 10 And Lengte < 38.6 And OptionButton1.Value = True Then
    q40 = q40 + 1
    e = "--> wordt een rol van 40 meter"
    End If
    
    
    'PE-RT-leiding
    If Lengte >= 88.6 And Lengte < 120 And OptionButton2.Value = True Then
    qpe120 = qpe120 + 1
    e = "--> wordt een rol van 120 meter"
    End If
    If Lengte >= 120 And OptionButton2.Value = True And CheckBox5.Value = True Then
    qpe120 = qpe120 + 1
    e = "--> wordt een rol van 120 meter"
    End If
    If Lengte >= 58.6 And Lengte < 88.6 And OptionButton2.Value = True Then
    qpe90 = qpe90 + 1
    e = "--> wordt een rol van 90 meter"
    End If
    If Lengte >= 10 And Lengte < 58.6 And OptionButton2.Value = True Then
    qpe60 = qpe60 + 1
    e = "--> wordt een rol van 60 meter"
    End If
    End If 'oude tekeningen
  
  
   'wth-zd
    If Lengte > 250 And OptionButton1.Value = True Then
    Label15 = " !!!..DE MAX. ROLLENGTE WORDT OVERSCHREDEN...!!!"
    Label15.BackColor = &HFFFF&
    'e = "--> ROL IS TE LANG.!!!"
    overschrijding1 = 1
    'frmLayerlijst.Height = 243
    End If
    'PE-RT
    If Lengte > 120 And OptionButton2.Value = True And CheckBox5.Value = False Then
    Label15 = " !!!..DE MAX. ROLLENGTE WORDT OVERSCHREDEN...!!!"
    Label15.BackColor = &HFFFF&
    'e = "--> ROL IS TE LANG.!!!"
    overschrijding1 = 1
    'frmLayerlijst.Height = 243
    End If
    
    
    If mystr = "groep" Then
    S = " = "
    Else
    S = "  = " ' HIERO
    End If
    
    If mystr = "wand_" Or mystr = "WAND_" Or mystr = "groep" Or mystr = "GROEP" Then
    If Lengte < 10 Or Lengte > 120 And OptionButton2.Value = True And CheckBox5.Value = False Or Lengte > 250 And OptionButton1.Value = True Then
    D = "LET OP!! " & laagobj.Name & S & Lengte & " meter."
    ListBox2.AddItem (D)
    overschrijding2 = 1
    Else
    D = laagobj.Name & S & Lengte & " meter"
    mylen = Len(D)
    'MsgBox mylen
    If mylen = 20 Then f = "     "
    If mylen = 22 Then f = "   "
    If mylen = 23 Then f = "  "
    If mylen = 24 Then f = " "
    D = D & f & e & wvaanwezig
    ListBox1.AddItem (D)
    End If
    End If
    
    If OptionButton1.Value = True Then
    TextBox2 = q250
    TextBox3 = q165
    TextBox4 = q125
    TextBox5 = q105
    TextBox6 = q90
    TextBox7 = q75
    TextBox8 = q63
    TextBox10 = q50
    TextBox11 = q40
    
      
    If TextBox2 = "" Then TextBox2 = "0"
    If TextBox3 = "" Then TextBox3 = "0"
    If TextBox4 = "" Then TextBox4 = "0"
    If TextBox5 = "" Then TextBox5 = "0"
    If TextBox6 = "" Then TextBox6 = "0"
    If TextBox7 = "" Then TextBox7 = "0"
    If TextBox8 = "" Then TextBox8 = "0"
    If TextBox10 = "" Then TextBox10 = "0"
    If TextBox11 = "" Then TextBox11 = "0"
    
    
    
    totaal2 = q250 + q165 + q125 + q105 + q90 + q75 + q63 + q50 + q40
    End If
    
    If OptionButton2.Value = True Then
    TextBox2 = qpe120
    TextBox3 = qpe90
    TextBox4 = qpe60
    TextBox5.Visible = False
    TextBox6.Visible = False
    TextBox7.Visible = False
    TextBox8.Visible = False
    TextBox10.Visible = False
    TextBox11.Visible = False
    
         
    If TextBox2 = "" Then TextBox2 = "0"
    If TextBox3 = "" Then TextBox3 = "0"
    If TextBox4 = "" Then TextBox4 = "0"
    If TextBox21 = "" Then TextBox21 = "0"
    If TextBox22 = "" Then TextBox22 = "0"
    If TextBox23 = "" Then TextBox23 = "0"
    If TextBox24 = "" Then TextBox24 = "0"
    Label1.Caption = "120 meter"
    Label3.Caption = "90 meter"
    Label5.Caption = "60 meter"
    Label7.Caption = Clear
    Label8.Caption = Clear
    Label10.Caption = Clear
    Label13.Caption = Clear
    Label21.Caption = Clear
    Label22.Caption = Clear
    
    totaal2 = qpe120 + qpe90 + qpe60
    End If
    Lengte = 0 'Lengte leeggooien voordat de volgende groep wordt gemeten
    zlengte = 0
    z = 0
    wvaanwezig = ""
  End If  'end if  mystr
 Next laagobj
 ProgressBar1.Value = minaantal
 Update
 
  Label16 = totaal2
  Label17 = " Totaal: " & totaal2 & " groep(en)"
 If q250 = 0 And q165 = 0 And q125 = 0 And q105 = 0 And q90 = 0 And q75 = 0 _
 And q63 = 0 And q50 = 0 And q40 = 0 And qpe120 = 0 And qpe90 = 0 And qpe60 = 0 Then
 Cmdprint.Enabled = False
 frmLayerlijst.Height = 422
 Label15.Caption = " !!!...GEEN GROEPLAYERS AANWEZIG...!!!"
 Label15.BackColor = &HFFFF&
 Else
 frmLayerlijst.Width = 488 ''''''''''''''''''''''''''''''''''''''''''HIER
 Cmdprint.Enabled = True
 End If
 If overschrijding1 = 1 Then frmLayerlijst.Height = 263 '243
 If overschrijding2 = 1 Then frmLayerlijst.Height = 346 '290
 If CheckBox5.Value = False Then
 Label24.Visible = True
 TextBox12.Visible = True
 Else
 Label24.Visible = False
 TextBox12.Visible = False
 End If
 If OptionButton2.Value = True Then
 CheckBox5.Visible = True
 Else
 CheckBox5.Visible = False
 End If
 
   'lijst rangschikken
  Dim Veld(0 To 500)
  Dim textstring2 As String
  
    For I = 0 To ListBox1.ListCount - 1
    textstring2 = ListBox1.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox1.Clear
 
  For x = 0 To UBound(Veld)
  If Veld(x) <> "" Then ListBox1.AddItem Veld(x)
  Next x
 TextBox12 = totalrollen
 TextBox20 = TextBox12
 TextBox26 = TextBox12
 If OptionButton2.Value = True Then CheckBox5.Enabled = False
 
Dim lognaam
lognaam = ThisDrawing.GetVariable("loginname")
lognaam = UCase(lognaam)
If lognaam = "GERARD" Then
   frmLayerlijst.Width = 488
   Call extr_control
End If
 
End Sub
Private Sub Cmdprint_Click()
Dim lognaam
lognaam = ThisDrawing.GetVariable("loginname")
lognaam = UCase(lognaam)
If lognaam = "ILONA" Then
   Call ILONA
  Else




Const ForReading = 1, ForWriting = 2, ForAppending = 8
Dim fs, f
Dim s1 As AcadSelectionSet
Set fs = CreateObject("Scripting.FileSystemObject")
teknaam = ThisDrawing.GetVariable("dwgname")
pad = ThisDrawing.GetVariable("dwgprefix")
usernaam = ThisDrawing.GetVariable("loginname")
Dim MyDate
MyDate = DateValue(Date)    ' Return a date.


Set f = fs.OpenTextFile("c:\acad2002\layerlijst.txt", ForAppending, -2)
    f.write "     " & "Tekenaar: " & usernaam & " |Datum: " & MyDate
    f.write Chr(13) + Chr(10)
    f.write Chr(13) + Chr(10)
    f.write "     " & pad
    f.write Chr(13) + Chr(10)
    f.write "     " & teknaam
    f.write Chr(13) + Chr(10)
    f.write Chr(13) + Chr(10)
    f.Close
    
If CheckBox5.Value = False Then
    teller = ListBox1.ListCount
    For I = 0 To teller - 1
       'Define the text object
        textstring = ListBox1.List(I)
        Set f = fs.OpenTextFile("c:\acad2002\layerlijst.txt", ForAppending, -2)
        f.write "     " & textstring
        f.write Chr(13) + Chr(10)
        f.Close
    Next I
    

    If OptionButton1.Value = True Then
    totaal1 = TextBox2 & " * 250|" & TextBox3 & " * 165|" & TextBox4 & " * 125|" & _
    TextBox5 & " * 105|" & TextBox6 & " * 90|" & TextBox7 & " * 75|" & _
    TextBox8 & " * 63|" & TextBox10 & " * 50|" & TextBox11 & " * 40"
    
    totaal2 = "Totaal: " & Label16 & " groepen. (WTH-ZD leiding)"
    roltel = Val(TextBox2) + Val(TextBox3) + Val(TextBox4) + Val(TextBox5) + Val(TextBox6) + _
    Val(TextBox7) + Val(TextBox8) + Val(TextBox10) + Val(TextBox11)
    Else
    totaal1 = TextBox2 & " * 120 | " & TextBox3 & " * 90 | " & TextBox4 & " * 60"
    totaal2 = "Totaal: " & Label16 & " groepen. (PE-RT leiding)"
    roltel = Val(TextBox2) + Val(TextBox3) + Val(TextBox4)
    End If
    eindrol = "Totaal: " & roltel & " rol(len)"
    compleet = "Totaal: " & TextBox12 & " meters."
    uitleg = "(WV) = Groep met wandverwarming"
    If TextBox13 <> "" Then aantalmeters = "Oppervlakte t.b.v.Isolatie/Netten: " & TextBox13 & " m2"
    
    Set f = fs.OpenTextFile("c:\acad2002\layerlijst.txt", ForAppending, -2)
        f.write "     " & "--------------------------------------------------------------------"
        f.write Chr(13) + Chr(10)
        f.write "     " & totaal1
        f.write Chr(13) + Chr(10)
        f.write "     " & totaal2
        f.write Chr(13) + Chr(10)
        f.write "     " & "--------------------------------------------------------------------"
        f.write Chr(13) + Chr(10)
        f.write "     " & eindrol
        f.write Chr(13) + Chr(10)
        f.write "     " & compleet
        f.write Chr(13) + Chr(10)
        f.write "     " & uitleg
        If TextBox13 <> 0 Then
        f.write Chr(13) + Chr(10)
        f.write "     " & aantalmeters
        End If
        f.Close
        
    teller2 = ListBox2.ListCount
    If frmLayerlijst.CheckBox4.Value = True Then
        Set f = fs.OpenTextFile("c:\acad2002\layerlijst.txt", ForAppending, -2)
        f.write Chr(13) + Chr(10)
        f.write Chr(13) + Chr(10)
        f.write "     " & "--------------------------------------------------------------------"
        f.write Chr(13) + Chr(10)
        f.write "     " & "Afwijkende rollengte's"
        f.write Chr(13) + Chr(10)
        f.Close
    For q = 0 To teller2 - 1
       'Define the text object
        textstring2 = ListBox2.List(q)
        Set f = fs.OpenTextFile("c:\acad2002\layerlijst.txt", ForAppending, -2)
        f.write "     " & textstring2
        f.write Chr(13) + Chr(10)
        f.Close
    Next q
    End If
Else  '800 meter rollen
    teller = ListBox1.ListCount
    For I = 0 To teller - 1
       'Define the text object
        textstring = ListBox1.List(I)
        textstring2 = Split(textstring, "wordt")
        Set f = fs.OpenTextFile("c:\acad2002\layerlijst.txt", ForAppending, -2)
        f.write "     " & textstring2(0)
        f.write Chr(13) + Chr(10)
        f.Close
    Next I
  
    totaal1 = TextBox21 & " * 800|" & TextBox22 & " * 120|" & TextBox23 & " * 90|" & TextBox24 & " * 60|"
    totaal2 = "Totaal: " & Label16 & " groepen. (PE-RT leiding)"
    roltel = Val(TextBox21) + Val(TextBox22) + Val(TextBox23) + Val(TextBox24)
    eindrol = "Totaal: " & roltel & " rol(len)"
    roltotal = (Val(TextBox20)) + (Val(TextBox25) * (Val(TextBox2) + Val(TextBox3) + Val(TextBox4)))
    compleet = "Totaal: " & roltotal & " meters.(inclusief restlengte - " & TextBox25 & " meter per groep.)"
    compleet2 = "Totaal: " & TextBox12 & " meters.(exclusief restlengte)"
    uitleg = "(WV) = Groep met wandverwarming"
    If TextBox13 <> "" Then aantalmeters = "Oppervlakte t.b.v.Isolatie/Netten: " & TextBox13 & " m2"
    
    Set f = fs.OpenTextFile("c:\acad2002\layerlijst.txt", ForAppending, -2)
        f.write "     " & "--------------------------------------------------------------------"
        f.write Chr(13) + Chr(10)
        f.write "     " & totaal1
        f.write Chr(13) + Chr(10)
        f.write "     " & totaal2
        f.write Chr(13) + Chr(10)
        f.write "     " & "--------------------------------------------------------------------"
        f.write Chr(13) + Chr(10)
        f.write "     " & eindrol
        f.write Chr(13) + Chr(10)
        f.write "     " & compleet2
        f.write Chr(13) + Chr(10)
        f.write "     " & compleet
        f.write Chr(13) + Chr(10)
        f.write "     " & uitleg
        If TextBox13 <> 0 Then
        f.write Chr(13) + Chr(10)
        f.write "     " & aantalmeters
        End If
        f.Close
        
    teller2 = ListBox2.ListCount
    If frmLayerlijst.CheckBox4.Value = True Then
        Set f = fs.OpenTextFile("c:\acad2002\layerlijst.txt", ForAppending, -2)
        f.write Chr(13) + Chr(10)
        f.write Chr(13) + Chr(10)
        f.write "     " & "--------------------------------------------------------------------"
        f.write Chr(13) + Chr(10)
        f.write "     " & "Afwijkende rollengte's"
        f.write Chr(13) + Chr(10)
        f.Close
    For q = 0 To teller2 - 1
       'Define the text object
        textstring2 = ListBox2.List(q)
        Set f = fs.OpenTextFile("c:\acad2002\layerlijst.txt", ForAppending, -2)
''''''        f.write Chr(13) + Chr(10)
''''''        f.write Chr(13) + Chr(10)
''''''        f.write "     " & "--------------------------------------------------------------------"
''''''        f.write Chr(13) + Chr(10)
''''''        f.write "     " & "Afwijkende rollengte's"
''''''        f.write Chr(13) + Chr(10)
        f.write "     " & textstring2
        f.write Chr(13) + Chr(10)
        f.Close
    Next q
    End If

End If  '800 meter rollen




    
Dim RetVal
RetVal = Shell("C:\acad2002\vba\layerlijst.bat", 1)    ' uitprinten textfile.

If TextBox14 > 30 Then ThisDrawing.Close
 If TextBox14 > 30 Then
  bestandnaam3 = TextBox16 & TextBox17 & "-meten" & ".dwg"
  Kill (bestandnaam3)
 End If
ThisDrawing.SendCommand "-layer" & vbCr & "Freeze" & vbCr & "oppervlakte" & vbCr & vbCr
End If 'ILONA
Unload Me
ThisDrawing.SendCommand "setvar" & vbCr & "acadlspasdoc" & vbCr & "1" & vbCr
End Sub
Sub LEIDINGSOORT()

'TextBox13 = ThisDrawing.GetVariable("userr2")

 For Each element In ThisDrawing.ModelSpace
        If element.ObjectName = "AcDbBlockReference" Then
            If UCase(element.Name) = "GROEPTEKSTBLOKNEW" Then
                Set symbool = element
                If symbool.HasAttributes Then
                    attributen = symbool.GetAttributes
                    For I = LBound(attributen) To UBound(attributen)
                         Set attribuut = attributen(I)
                         If attribuut.TagString = "LEIDINGSOORT" Then WSL = attribuut.textstring
                         If attribuut.TagString = "UNITNUMMER" Then UNITSjek = attribuut.textstring
                    Next I
                End If
            End If
        End If
    Next element
If WSL = "WTH-ZD" Then frmLayerlijst.OptionButton1 = True
If WSL = "PE-RT" Then
     CheckBox5.Visible = True
     frmLayerlijst.OptionButton2 = True
End If
UNITSJEK1 = Len(UNITSjek)
If UNITSJEK1 = 1 Then frmLayerlijst.CheckBox3.Value = True
End Sub
Private Sub cmdAfsluiten_Click()
'checkopexport = Right(TextBox20, 5)
If TextBox18 <> "" Then
 checkopexport = Split(TextBox18, ".")
 checkopexport1 = Right(checkopexport(0), 5)
 If checkopexport1 = "meten" Then ThisDrawing.Close
 bestandnaam3 = TextBox16 & TextBox17 & "-meten" & ".dwg"
 'Kill (bestandnaam3)
End If
ThisDrawing.SendCommand "-layer" & vbCr & "Freeze" & vbCr & "oppervlakte" & vbCr & vbCr
Unload Me
'ThisDrawing.SendCommand "setvar" & vbCr & "acadlspasdoc" & vbCr & "1" & vbCr
End Sub

Sub extreemtek()

'Call zoekblad(bladnummer)
'TextBox14 = bladnummer

 'If TextBox14 = "" Then
 '    Exit Sub
 'End If
 
 
TextBox14 = Clear
For Each layerObj In ThisDrawing.Layers
     If Left(layerObj.Name, 5) = "groep" Then TextBox14 = (Val(TextBox14)) + 1  'aantal groepen
Next 'layerobj
If TextBox14 = "" Then TextBox14 = 0

For Each element2 In ThisDrawing.ModelSpace
      If element2.ObjectName = "AcDbBlockReference" Then
      If UCase(element2.Name) = "KADERLOGO" Or UCase(element2.Name) = "LOGOTGH" Then
      Set symbool = element2
        If symbool.HasAttributes Then
        attributen = symbool.GetAttributes
        For k = LBound(attributen) To UBound(attributen)
        Set attribuut = attributen(k)
        If attribuut.TagString = "SCHAAL" Then schaalfaktor = attribuut.textstring
        Next k
       
      End If
      End If
      End If
Next element2

vartab = ThisDrawing.GetVariable("EXTMAX")

' A3 T/M A0+
If vartab(0) >= 2045 And vartab(0) <= 2055 Or vartab(0) >= 2915 And vartab(0) <= 2925 _
    Or vartab(0) >= 4175 And vartab(0) <= 4185 Or vartab(0) >= 5890 And vartab(0) <= 5900 _
    Or vartab(0) >= 7840 And vartab(0) <= 7850 Then
    maxwaarde = 1
Else
    maxwaarde = 2
End If
If vartab(0) >= 16715 And vartab(0) <= 16725 Or vartab(0) >= 23575 And vartab(0) <= 23585 _
    Or vartab(0) >= 31375 And vartab(0) <= 31385 Then
    maxwaarde = 4
End If
Update

If schaalfaktor = "1:50" And maxwaarde = 1 Then scaal = 1
If schaalfaktor = "1:100" And maxwaarde = 1 Then scaal = 2
If schaalfaktor = "1:200" And maxwaarde = 1 Then scaal = 4

If schaalfaktor = "1:50" And maxwaarde = 2 Then scaal = 0.5
If schaalfaktor = "1:100" And maxwaarde = 2 Then scaal = 1
If schaalfaktor = "1:200" And maxwaarde = 2 Then scaal = 2

If schaalfaktor = "1:200" And maxwaarde = 4 Then scaal = 1
TextBox19.Value = scaal

teknaam = ThisDrawing.GetVariable("dwgname")    'teknaam = ThisDrawing.GetVariable("dwgname")
TextBox15 = teknaam
TextBox16 = "c:\acad2002\"  'pad = ThisDrawing.GetVariable("dwgprefix")
teknaam1 = Split(teknaam, ("."))                'teknaam1 = Split(teknaam, ("."))

         Dim mystr As Variant
         mystr = Len(teknaam)
         over = mystr - 4 'aantal karakters
         teknaam6 = Left(teknaam, over)

'TextBox18 = teknaam1(0)
TextBox17 = teknaam6


'aantal groepen groter dan 30 ????
If TextBox14 > 30 Then
Call exportuserr2
frmLayerlijst.Hide

 
'bestandnaam2 = pad & teknaam1(0) & "-export" & ".dwg"
bestandnaam2 = TextBox16 & TextBox17 & "-meten" & ".dwg"
TextBox18 = bestandnaam2

'Kill (bestandnaam)
'Call zoekblad(bladnummer)

'''ThisDrawing.SendCommand "-layer" & vbCr & "unlock" & vbCr & "*" & vbCr & vbCr
'''ThisDrawing.SendCommand "-layer" & vbCr & "set" & vbCr & "0" & vbCr & vbCr
'''ThisDrawing.SendCommand "-layer" & vbCr & "Freeze" & vbCr & "*" & vbCr & vbCr
'''ThisDrawing.SendCommand "-layer" & vbCr & "Thaw" & vbCr & "groep*" & vbCr & vbCr
'''ThisDrawing.SendCommand "-layer" & vbCr & "Thaw" & vbCr & "gt" & vbCr & vbCr
'''
'''ThisDrawing.SendCommand "_copyclip" & vbCr & "all" & vbCr & vbCr
'''ThisDrawing.SendCommand "-layer" & vbCr & "Thaw" & vbCr & "*" & vbCr & vbCr

'''templatenaam = ThisDrawing.GetVariable("acadver")
'''If templatenaam = "15.06s (LMS Tech)" Then ThisDrawing.Application.Documents.Add ("acad2000.dwt")
''''If templatenaam = "16.0s (LMS Tech)" Then ThisDrawing.Application.Documents.Add ("acad2004.dwt")
'''If templatenaam >= "16.0s (LMS Tech)" Then
'''ThisDrawing.SendCommand "setvar" & vbCr & "acadlspasdoc" & vbCr & "0" & vbCr
'''ThisDrawing.Application.Documents.Add ("autocad.dwt")
'''
'''ThisDrawing.SendCommand "_pasteclip" & vbCr & "0,0" & vbCr
'''
'''ThisDrawing.SaveAs (bestandnaam2)
'''ZoomExtents
End If


End Sub
Sub extr_control()

Dim element As Object
    For Each element In ThisDrawing.ModelSpace
          If element.ObjectName = "AcDbBlockReference" Then
          If element.Name = "GROEPTEKSTBLOKNEW" Or element.Name = "groeptekstbloknew" Then
          Set symbool = element
            If symbool.HasAttributes Then
            attributen = symbool.GetAttributes
            For I = LBound(attributen) To UBound(attributen)
            Set attribuut = attributen(I)
             If attribuut.TagString = "GROEPTEKST" Then gra = attribuut.textstring
                If attribuut.TagString = "ROLLENGTE" And attribuut.textstring <> " " Then
                vul = gra & " | " & attribuut.textstring
                ListBox3.AddItem (vul)
                End If
           Next I
    End If
    End If
    End If
    Next element
    
    
 Dim Veld(0 To 500)
  Dim textstring2 As String
  
    For I = 0 To ListBox3.ListCount - 1
    textstring2 = ListBox3.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox3.Clear
 
  For x = 0 To UBound(Veld)
  If Veld(x) <> "" Then ListBox3.AddItem Veld(x)
  Next x
  Label34 = ListBox3.ListCount
  
  
  
  Dim jet As String
  Dim textstring6 As String
For k = 0 To ListBox1.ListCount - 1
    textstring5 = ListBox1.List(k)
    textstring6 = ListBox3.List(k)
   
    jel = Split(textstring5, "=") 'groeptekst
    'MsgBox Len(jel(0)) 'groeptekst
    jek = Split(jel(1), "-->")
    'MsgBox jek(1)
    jem = Split(jek(1), " ")
    'MsgBox Len(jem(5)) 'rollengte
    jet = jel(0) & "| " & jem(5) & " meter"
        If jet <> textstring6 Then
          TTS = "[layers]- " & jet & " -FOUT- " & textstring6 & " -[groeptekstblok]"
          ListBox2.AddItem (TTS)
          frmLayerlijst.Height = 422
        End If
    'MsgBox JET & " - " & TEXTSTRING6
    R = Len(jet)
    S = Len(textstring6)
   ' MsgBox R & " - " & S
Next k
ListBox2.Width = 345
 
End Sub
Sub ILONA()
Const ForReading = 1, ForWriting = 2, ForAppending = 8
Dim fs, f
Dim s1 As AcadSelectionSet
Set fs = CreateObject("Scripting.FileSystemObject")
teknaam = ThisDrawing.GetVariable("dwgname")
pad = ThisDrawing.GetVariable("dwgprefix")
usernaam = ThisDrawing.GetVariable("loginname")
Dim MyDate
MyDate = DateValue(Date)    ' Return a date.


         Dim mystr As Variant
         mystr = Len(teknaam)
         over = mystr - 4 'aantal karakters
         teknaam6 = Left(teknaam, over)

txtbest = pad & "\" & teknaam6 & ".txt"


Set f = fs.OpenTextFile(txtbest, ForAppending, -2)
    f.write "     " & "Tekenaar: " & usernaam & " |Datum: " & MyDate
    f.write Chr(13) + Chr(10)
    f.write Chr(13) + Chr(10)
    f.write "     " & pad
    f.write teknaam
    f.write Chr(13) + Chr(10)
    f.write Chr(13) + Chr(10)
    f.Close
    
If CheckBox5.Value = False Then
    teller = ListBox1.ListCount
    For I = 0 To teller - 1
       'Define the text object
        textstring = ListBox1.List(I)
        Set f = fs.OpenTextFile(txtbest, ForAppending, -2)
        f.write "     " & textstring
        f.write Chr(13) + Chr(10)
        f.Close
    Next I
    

    If OptionButton1.Value = True Then
    totaal1 = TextBox2 & " * 250|" & TextBox3 & " * 165|" & TextBox4 & " * 125|" & _
    TextBox5 & " * 105|" & TextBox6 & " * 90|" & TextBox7 & " * 75|" & _
    TextBox8 & " * 63|" & TextBox10 & " * 50|" & TextBox11 & " * 40"
    
    totaal2 = "Totaal: " & Label16 & " groepen. (WTH-ZD leiding)"
    roltel = Val(TextBox2) + Val(TextBox3) + Val(TextBox4) + Val(TextBox5) + Val(TextBox6) + _
    Val(TextBox7) + Val(TextBox8) + Val(TextBox10) + Val(TextBox11)
    Else
    totaal1 = TextBox2 & " * 120 | " & TextBox3 & " * 90 | " & TextBox4 & " * 60"
    totaal2 = "Totaal: " & Label16 & " groepen. (PE-RT leiding)"
    roltel = Val(TextBox2) + Val(TextBox3) + Val(TextBox4)
    End If
    eindrol = "Totaal: " & roltel & " rol(len)"
    compleet = "Totaal: " & TextBox12 & " meters."
    uitleg = "(WV) = Groep met wandverwarming"
    If TextBox13 <> "" Then aantalmeters = "Oppervlakte t.b.v.Isolatie/Netten: " & TextBox13 & " m2"
    
    Set f = fs.OpenTextFile(txtbest, ForAppending, -2)
        f.write "     " & "--------------------------------------------------------------------"
        f.write Chr(13) + Chr(10)
        f.write "     " & totaal1
        f.write Chr(13) + Chr(10)
        f.write "     " & totaal2
        f.write Chr(13) + Chr(10)
        f.write "     " & "--------------------------------------------------------------------"
        f.write Chr(13) + Chr(10)
        f.write "     " & eindrol
        f.write Chr(13) + Chr(10)
        f.write "     " & compleet
        f.write Chr(13) + Chr(10)
        f.write "     " & uitleg
        If TextBox13 <> 0 Then
        f.write Chr(13) + Chr(10)
        f.write "     " & aantalmeters
        End If
        f.Close
        
    teller2 = ListBox2.ListCount
    If frmLayerlijst.CheckBox4.Value = True Then
        Set f = fs.OpenTextFile(txtbest, ForAppending, -2)
        f.write Chr(13) + Chr(10)
        f.write Chr(13) + Chr(10)
        f.write "     " & "--------------------------------------------------------------------"
        f.write Chr(13) + Chr(10)
        f.write "     " & "Afwijkende rollengte's"
        f.write Chr(13) + Chr(10)
        f.Close
    For q = 0 To teller2 - 1
       'Define the text object
        textstring2 = ListBox2.List(q)
        Set f = fs.OpenTextFile(txtbest, ForAppending, -2)
        f.write "     " & textstring2
        f.write Chr(13) + Chr(10)
        f.Close
    Next q
    End If
Else  '800 meter rollen
    teller = ListBox1.ListCount
    For I = 0 To teller - 1
       'Define the text object
        textstring = ListBox1.List(I)
        textstring2 = Split(textstring, "wordt")
        Set f = fs.OpenTextFile(txtbest, ForAppending, -2)
        f.write "     " & textstring2(0)
        f.write Chr(13) + Chr(10)
        f.Close
    Next I
  
    totaal1 = TextBox21 & " * 800|" & TextBox22 & " * 120|" & TextBox23 & " * 90|" & TextBox24 & " * 60|"
    totaal2 = "Totaal: " & Label16 & " groepen. (PE-RT leiding)"
    roltel = Val(TextBox21) + Val(TextBox22) + Val(TextBox23) + Val(TextBox24)
    eindrol = "Totaal: " & roltel & " rol(len)"
    roltotal = (Val(TextBox20)) + (Val(TextBox25) * (Val(TextBox2) + Val(TextBox3) + Val(TextBox4)))
    compleet = "Totaal: " & roltotal & " meters.(inclusief restlengte - " & TextBox25 & " meter per groep.)"
    compleet2 = "Totaal: " & TextBox12 & " meters.(exclusief restlengte)"
    uitleg = "(WV) = Groep met wandverwarming"
    If TextBox13 <> "" Then aantalmeters = "Oppervlakte t.b.v.Isolatie/Netten: " & TextBox13 & " m2"
    
    Set f = fs.OpenTextFile(txtbest, ForAppending, -2)
        f.write "     " & "--------------------------------------------------------------------"
        f.write Chr(13) + Chr(10)
        f.write "     " & totaal1
        f.write Chr(13) + Chr(10)
        f.write "     " & totaal2
        f.write Chr(13) + Chr(10)
        f.write "     " & "--------------------------------------------------------------------"
        f.write Chr(13) + Chr(10)
        f.write "     " & eindrol
        f.write Chr(13) + Chr(10)
        f.write "     " & compleet2
        f.write Chr(13) + Chr(10)
        f.write "     " & compleet
        f.write Chr(13) + Chr(10)
        f.write "     " & uitleg
        If TextBox13 <> 0 Then
        f.write Chr(13) + Chr(10)
        f.write "     " & aantalmeters
        End If
        f.Close
        
    teller2 = ListBox2.ListCount
    If frmLayerlijst.CheckBox4.Value = True Then
        Set f = fs.OpenTextFile(txtbest, ForAppending, -2)
        f.write Chr(13) + Chr(10)
        f.write Chr(13) + Chr(10)
        f.write "     " & "--------------------------------------------------------------------"
        f.write Chr(13) + Chr(10)
        f.write "     " & "Afwijkende rollengte's"
        f.write Chr(13) + Chr(10)
        f.Close
    For q = 0 To teller2 - 1
       'Define the text object
        textstring2 = ListBox2.List(q)
        Set f = fs.OpenTextFile(txtbest, ForAppending, -2)
''''''        f.write Chr(13) + Chr(10)
''''''        f.write Chr(13) + Chr(10)
''''''        f.write "     " & "--------------------------------------------------------------------"
''''''        f.write Chr(13) + Chr(10)
''''''        f.write "     " & "Afwijkende rollengte's"
''''''        f.write Chr(13) + Chr(10)
        f.write "     " & textstring2
        f.write Chr(13) + Chr(10)
        f.Close
    Next q
    End If

End If  '800 meter rollen

Dim RetVal
Dim retval2

RetVal = "> HP LaserJet 4100"
retval2 = "type " & txtbest & " " & RetVal & vbCr


ThisDrawing.SendCommand retval2


If TextBox14 > 30 Then ThisDrawing.Close
 If TextBox14 > 30 Then
  bestandnaam3 = TextBox16 & TextBox17 & "-meten" & ".dwg"
  Kill (bestandnaam3)
 End If
ThisDrawing.SendCommand "-layer" & vbCr & "Freeze" & vbCr & "oppervlakte" & vbCr & vbCr
Unload Me
End Sub


''''''''''''''''''''''''''''''''''''''''''' nieuwe layerlijst''''''''''''''''''''''''''''''''''''''''''''''''''''
''''''''''''''''''''''''''''''''''''''''''' nieuwe layerlijst''''''''''''''''''''''''''''''''''''''''''''''''''''
''''''''''''''''''''''''''''''''''''''''''' nieuwe layerlijst''''''''''''''''''''''''''''''''''''''''''''''''''''

Private Sub CommandButton2_Click()
For Each element10 In ThisDrawing.ModelSpace
      If element10.ObjectName = "AcDbBlockReference" Then
      If element10.Name = "Mat_spe_ZD" Or element10.Name = "Mat_spe_ZD_1627" Or element10.Name = "Mat_spe_ZD_1627500" Then
                 Set symbool = element10
                 If symbool.HasAttributes Then
                    attributen = symbool.GetAttributes
                    For j = LBound(attributen) To UBound(attributen)
                    Set attribuut = attributen(j)
                      ' wth-zd 20*3,4 of wth-zd 16*2,7
                      If attribuut.TagString = "RNU" Then zd20rnu1 = attribuut.textstring
                      If attribuut.TagString = "REGELUNITTYPE" Then zd20rnu2 = attribuut.textstring
                      If attribuut.TagString = "WTHZD" Then zd20rnu33 = attribuut.textstring
                      If attribuut.TagString = "WTH250" Then zd20rnu3 = attribuut.textstring
                      If attribuut.TagString = "WTH165" Then zd20rnu4 = attribuut.textstring
                      If attribuut.TagString = "WTH125" Then zd20rnu5 = attribuut.textstring
                      If attribuut.TagString = "WTH105" Then zd20rnu6 = attribuut.textstring
                      If attribuut.TagString = "WTH90" Then zd20rnu7 = attribuut.textstring
                      If attribuut.TagString = "WTH75" Then zd20rnu8 = attribuut.textstring
                      If attribuut.TagString = "WTH63" Then zd20rnu9 = attribuut.textstring
                      If attribuut.TagString = "WTH50" Then zd20rnu10 = attribuut.textstring
                      If attribuut.TagString = "WTH40" Then zd20rnu11 = attribuut.textstring
                      If attribuut.TagString = "PE" Then zd20rnu33 = attribuut.textstring
                      If attribuut.TagString = "LMETER" Then lm = attribuut.textstring
                    Next j

                         If zd20rnu33 = "WTH-ZD 20*3,4 mm" Then
                         total1 = zd20rnu1 & "#" & zd20rnu2 & "#" & zd20rnu33 & "|" & zd20rnu3 & " * 250|" & zd20rnu4 & " * 165|" & _
                         zd20rnu5 & " * 125|" & zd20rnu6 & " * 105|" & zd20rnu7 & " * 90|" & zd20rnu8 & " * 75|" & _
                         zd20rnu9 & " * 63|" & zd20rnu10 & " * 50|" & zd20rnu11 & " * 40"
                         End If
                       
                         If zd20rnu33 = "WTH-ZD 16*2,7 mm" And lm = "" Then
                         total1 = zd20rnu1 & "#" & zd20rnu2 & "#" & zd20rnu33 & "|" & _
                         zd20rnu6 & " * 105|" & zd20rnu7 & " * 90|" & zd20rnu8 & " * 75|" & zd20rnu9 & " * 63|"
                         End If
                         
                         If zd20rnu33 = "WTH-ZD 16*2,7 mm" And lm <> "" Then
                         total1 = zd20rnu1 & "#" & zd20rnu2 & "#" & zd20rnu33 ' & "|" & lm & " meters"
                         End If
                         
                  End If

            frmLayerlijst.ListBox5.AddItem (total1)
        End If
      End If
  Next element10
  
For Each element50 In ThisDrawing.ModelSpace
      If element50.ObjectName = "AcDbBlockReference" Then
      If element50.Name = "Mat_spe_ZDringleiding" Then
                 Set symbool = element50
                 If symbool.HasAttributes Then
                    attributen = symbool.GetAttributes
                    For j = LBound(attributen) To UBound(attributen)
                    Set attribuut = attributen(j)
                      ' wth-zd 20*3,4 of wth-zd 16*2,7
                      If attribuut.TagString = "RNU" Then zd20rnu1 = attribuut.textstring
                      If attribuut.TagString = "REGELUNITTYPE" Then zd20rnu2 = attribuut.textstring
                      If attribuut.TagString = "WTHZD" Then zd20rnu33 = attribuut.textstring
                      If attribuut.TagString = "WTH250" Then zd20rnu3 = attribuut.textstring
                      If attribuut.TagString = "WTH165" Then zd20rnu4 = attribuut.textstring
                      If attribuut.TagString = "WTH125" Then zd20rnu5 = attribuut.textstring
                      If attribuut.TagString = "WTH105" Then zd20rnu6 = attribuut.textstring
                      If attribuut.TagString = "WTH90" Then zd20rnu7 = attribuut.textstring
                      If attribuut.TagString = "WTH75" Then zd20rnu8 = attribuut.textstring
                      If attribuut.TagString = "WTH63" Then zd20rnu9 = attribuut.textstring
                      If attribuut.TagString = "WTH50" Then zd20rnu10 = attribuut.textstring
                      If attribuut.TagString = "WTH40" Then zd20rnu11 = attribuut.textstring
                      If attribuut.TagString = "PE" Then zd20rnu33 = attribuut.textstring
                      If attribuut.TagString = "LMETER" Then lm = attribuut.textstring
                    Next j

                         If zd20rnu33 = "WTH-ZD 20*3,4 mm" Then
                         total1 = zd20rnu1 & "#" & zd20rnu2 & "#" & zd20rnu33 & "|" & zd20rnu3 & " * 250|" & zd20rnu4 & " * 165|" & _
                         zd20rnu5 & " * 125|" & zd20rnu6 & " * 105|" & zd20rnu7 & " * 90|" & zd20rnu8 & " * 75|" & _
                         zd20rnu9 & " * 63|" & zd20rnu10 & " * 50|" & zd20rnu11 & " * 40"
                         End If
                                               
                  End If

            frmLayerlijst.ListBox5.AddItem (total1)
        End If
      End If
  Next element50


For Each element10 In ThisDrawing.ModelSpace
      If element10.ObjectName = "AcDbBlockReference" Then
      If element10.Name = "Mat_spe_PE" Or element10.Name = "Mat_spe_PEringleiding" Then
                 Set symbool = element10
                 If symbool.HasAttributes Then
                    attributen = symbool.GetAttributes
                    For j = LBound(attributen) To UBound(attributen)
                    Set attribuut = attributen(j)
                      ' PE-RT 16*2
                      If attribuut.TagString = "RNU" Then zd20rnu1 = attribuut.textstring
                      If attribuut.TagString = "REGELUNITTYPE" Then zd20rnu2 = attribuut.textstring
                      If attribuut.TagString = "PE" Then zd20rnu33 = attribuut.textstring
                      If attribuut.TagString = "PE120" Then zd20rnu4 = attribuut.textstring
                      If attribuut.TagString = "PE90" Then zd20rnu5 = attribuut.textstring
                      If attribuut.TagString = "PE60" Then zd20rnu6 = attribuut.textstring
                      
                    Next j

                         If zd20rnu33 = "PE-RT 16*2 mm" Then
                         total1 = zd20rnu1 & "#" & zd20rnu2 & "#" & zd20rnu33 & "|" & _
                         zd20rnu4 & " * 120|" & zd20rnu5 & " * 90|" & zd20rnu6 & " * 60|"
                         End If
                         
                         If zd20rnu33 = "PE-RT 14*2 mm" Then
                         total1 = zd20rnu1 & "#" & zd20rnu2 & "#" & zd20rnu33 & "|" & _
                         zd20rnu5 & " * 90|" & zd20rnu6 & " * 60|"
                         End If
                
                  End If


            frmLayerlijst.ListBox5.AddItem (total1)
        End If
      End If
  Next element10
  
  For Each element20 In ThisDrawing.ModelSpace
      If element20.ObjectName = "AcDbBlockReference" Then
      If element20.Name = "Mat_spe_PE800" Then
                 Set symbool = element20
                 If symbool.HasAttributes Then
                    attributen = symbool.GetAttributes
                    For j = LBound(attributen) To UBound(attributen)
                    Set attribuut = attributen(j)
                      ' PE-RT 16*2
                      If attribuut.TagString = "RNU" Then zd20rnu1 = attribuut.textstring
                      If attribuut.TagString = "REGELUNITTYPE" Then zd20rnu2 = attribuut.textstring
                      If attribuut.TagString = "PE" Then zd20rnu33 = attribuut.textstring
                      If attribuut.TagString = "LMETER" Then lm = attribuut.textstring
                      
                      
                    Next j

                         If zd20rnu33 = "PE-RT 16*2 mm" And lm <> "" Then
                         total1 = zd20rnu1 & "#" & zd20rnu2 & "#" & zd20rnu33 ' & "|" & lm & " meters"
                         End If
  
                         
                        
                  End If


            frmLayerlijst.ListBox5.AddItem (total1)
        End If
      End If
  Next element20

For Each element30 In ThisDrawing.ModelSpace
      If element30.ObjectName = "AcDbBlockReference" Then
      If element30.Name = "Mat_spe_ALUringleiding" Then
                 Set symbool = element30
                 If symbool.HasAttributes Then
                    attributen = symbool.GetAttributes
                    For j = LBound(attributen) To UBound(attributen)
                    Set attribuut = attributen(j)
                      ' PE-RT 16*2
                      If attribuut.TagString = "RNU" Then zd20rnu1 = attribuut.textstring
                      If attribuut.TagString = "REGELUNITTYPE" Then zd20rnu2 = attribuut.textstring
                      If attribuut.TagString = "ALU" Then zd20rnu33 = attribuut.textstring
                      If attribuut.TagString = "ALU200" Then zd20rnu4 = attribuut.textstring
                      If attribuut.TagString = "ALU100" Then zd20rnu5 = attribuut.textstring
                      If attribuut.TagString = "ALU50" Then zd20rnu6 = attribuut.textstring


                    Next j

                         If zd20rnu33 = "ALUFLEX 16*2 mm" Then
                         total1 = zd20rnu1 & "#" & zd20rnu2 & "#" & zd20rnu33 & "|" & _
                         zd20rnu4 & " * 200|" & zd20rnu5 & " * 100|" & zd20rnu6 & " * 50|"
                         End If


                  End If


            frmLayerlijst.ListBox5.AddItem (total1)
        End If
      End If
  Next element30
  
  
  'lijst rangschikken
  Dim Veld(0 To 500)
  Dim textstring2 As String
  
    For I = 0 To ListBox5.ListCount - 1
    textstring2 = ListBox5.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox5.Clear
 
  For x = 0 To UBound(Veld)
  If Veld(x) <> "" Then ListBox5.AddItem Veld(x)
  Next x
  
 Call splitting
End Sub
Sub splitting()

teller4 = frmLayerlijst.ListBox5.ListCount

              
          For k = 0 To teller4 - 1
          
            'Define the text object
            text5 = Split(frmLayerlijst.ListBox5.List(k), "#")  'unitnummer
                    

              frmLayerlijst.Caption = "Unit: " & text5(0) & " (totaal: " & teller4 & " units)"
                a = text5(0): b = text5(1): C = text5(2)
                Call splitverder(a, b, C)
         
          Next k
          
        TT = ThisDrawing.GetVariable("USERR2")
        If TT <> "" Then aantalmeters = "Oppervlakte t.b.v.Isolatie/Netten: " & TT & " m2"
        frmLayerlijst.ListBox4.AddItem (aantalmeters)
End Sub
Sub splitverder(a, b, C)
' ListBox6.Clear
Update
On Error Resume Next

Dim element400 As Object
For Each element400 In ThisDrawing.ModelSpace
      If element400.ObjectName = "AcDbBlockReference" Then
      If element400.Name = "GROEPTEKSTBLOKNEW" Or element400.Name = "groeptekstbloknew" Then
      Set symbool = element400
        If symbool.HasAttributes Then
        attributen = symbool.GetAttributes
        For I = LBound(attributen) To UBound(attributen)
        Set attribuut = attributen(I)
        If attribuut.TagString = "UNITNUMMER" Or attribuut.TagString = "unitnummer" Then
           m = attribuut.textstring
           If m = a Then

           For j = LBound(attributen) To UBound(attributen)
           Set attribuut = attributen(j)
            
            
'''                               If attribuut.TagString = "RINGLEIDING" And attribuut.textstring = "" Then attribuut.textstring = RL
'''                               If attribuut.TagString = "LEIDINGSOORT" And attribuut.textstring = "" Then attribuut.textstring = LW
'''                               If attribuut.TagString = "UNITNUMMER" And attribuut.textstring = "" Then attribuut.textstring = unitonder10 & frmGroeptekst.TextBox9
                               If attribuut.TagString = "GROEPTEKST" And attribuut.textstring <> " " Then groepsnummer = attribuut.textstring
'''                               If attribuut.TagString = "HOHAFSTAND" And attribuut.textstring = "" Then attribuut.textstring = hohafstand
                               If attribuut.TagString = "TLVL" Then tvl = attribuut.textstring  '  And attribuut.textstring <> " "
                               If attribuut.TagString = "ROLLENGTE" Then totallengte = attribuut.textstring
                               If attribuut.TagString = "RINGLEIDING" Then ring = attribuut.textstring
                                
'''                               If attribuut.TagString = "WERKLENGTE" And attribuut.textstring = "" Then attribuut.textstring = "nee"
'''                               If attribuut.TagString = "WANDHOOGTE" And check_layernaam = "groe" And attribuut.textstring = "" Then attribuut.textstring = " "
'''                               If attribuut.TagString = "WANDHOOGTE" And check_layernaam = "wand" And attribuut.textstring = "" Then attribuut.textstring = wandhoogte & " meter hoog"
           Next j
           

        End If 'TEXTBOX 9

        End If
      Next I
      
            If m = a And ring <> "RM" Then
            D = groepsnummer & " |" & tvl & " ->" & totallengte
            frmLayerlijst.ListBox6.AddItem (D)
            tvl = Split(tvl, " ")
            frmLayerlijst.TextBox28 = (Val(frmLayerlijst.TextBox28)) + tvl(0)
            Else
            tvl = Split(tvl, " ")
            frmLayerlijst.TextBox28 = (Val(frmLayerlijst.TextBox28)) + tvl(0)
            End If
     tvl = ""
         
End If
       
         
        
End If
End If
Next element400

If m = a And ring <> "RM" Then
e = "Unit:" & a & "|" & b & "|" & frmLayerlijst.TextBox28 & " meter."
frmLayerlijst.ListBox6.AddItem (e)
Else
e = a & "|" & b & "|" & frmLayerlijst.TextBox28 & " meter."
frmLayerlijst.ListBox6.AddItem (e)
End If

frmLayerlijst.TextBox28 = 0

'lijst rangschikken
  Dim Veld(0 To 500)
  Dim textstring2 As String
  
    For I = 0 To frmLayerlijst.ListBox6.ListCount - 1
    textstring2 = frmLayerlijst.ListBox6.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox6.Clear
 
  For x = 0 To UBound(Veld)
  If Veld(x) <> "" Then frmLayerlijst.ListBox6.AddItem Veld(x)
  Next x
frmLayerlijst.ListBox6.AddItem (C)
frmLayerlijst.ListBox6.AddItem ("------------------------------------")


Call verder2
End Sub
Sub verder2()
    teller = frmLayerlijst.ListBox6.ListCount
    For I = 0 To teller - 1
       'Define the text object
        textstring = frmLayerlijst.ListBox6.List(I)
        f = Right(textstring, 2)
        If f <> "> " Then
        frmLayerlijst.ListBox4.AddItem (textstring)
        End If
    Next I



  frmLayerlijst.ListBox6.Clear

End Sub
Private Sub commandbutton4_click()

Const ForReading = 1, ForWriting = 2, ForAppending = 8
Dim fs, f
Dim s1 As AcadSelectionSet
Set fs = CreateObject("Scripting.FileSystemObject")
teknaam = ThisDrawing.GetVariable("dwgname")
pad = ThisDrawing.GetVariable("dwgprefix")
usernaam = ThisDrawing.GetVariable("loginname")
Dim MyDate
MyDate = DateValue(Date)    ' Return a date.


Set f = fs.OpenTextFile("c:\acad2002\layerlijst.txt", ForAppending, -2)
    f.write "   " & "Tekenaar: " & usernaam & " |Datum: " & MyDate
    f.write Chr(13) + Chr(10)
    f.write Chr(13) + Chr(10)
    f.write "   " & pad
    f.write Chr(13) + Chr(10)
    f.write "   " & teknaam
    f.write Chr(13) + Chr(10)
    f.write Chr(13) + Chr(10)
    f.Close
    
    teller = ListBox4.ListCount
    For I = 0 To teller - 1
       'Define the text object
        textstring = ListBox4.List(I)
        Set f = fs.OpenTextFile("c:\acad2002\layerlijst.txt", ForAppending, -2)
        f.write "   " & textstring
        f.write Chr(13) + Chr(10)
        f.Close
    Next I
    

 
    
Dim RetVal
RetVal = Shell("C:\acad2002\vba\layerlijst.bat", 1)    ' uitprinten textfile.

ThisDrawing.SendCommand "-layer" & vbCr & "Freeze" & vbCr & "oppervlakte" & vbCr & vbCr

Unload Me
End Sub

Attribute VB_Name = "frmRuimtenaam"
Attribute VB_Base = "0{C7D98B11-4576-41CD-B759-31815E0CE00F}{043E61E9-4D15-4BCD-B08A-48CEACC1C346}"
Attribute VB_GlobalNameSpace = False
Attribute VB_Creatable = False
Attribute VB_PredeclaredId = True
Attribute VB_Exposed = False
Attribute VB_TemplateDerived = False
Attribute VB_Customizable = False

'05-11-2004 RUIMTENAAM PLAATSEN
'M.Bosch en G.C.Haak

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
Call uitlezenTXT
End Sub

Private Sub CommandButton1_Click()
waarde2 = 0
If TextBox2 = "" Then
samenvoegbox = TextBox1 & Space(1)
samenvoegbox = Split(samenvoegbox, " ")
samenvoegbox = samenvoegbox(0)
Else
samenvoegbox = TextBox1 & Space(1)
samenvoegbox = Split(samenvoegbox, " ")
samenvoegbox = samenvoegbox(0) & Space(1) & TextBox2
End If

For I = 0 To ListBox1.ListCount - 1
waarde1 = ListBox1.List(I)
If samenvoegbox = waarde1 Then
MsgBox "Staat al in de lijst"
waarde2 = 1
End If
Next I

If waarde2 <> 1 Then
ListBox1.AddItem (samenvoegbox)
bestand10 = "g:\tekeningen\ruimtenaam.txt"
Const ForReading = 1, ForWriting = 2, ForAppending = 8
Const TristateUseDefault = -2, TristateTrue = -1, TristateFalse = 0

Dim fs, a, vullistbox1
Set fs = CreateObject("Scripting.FileSystemObject")
Set a = fs.OpenTextFile(bestand10, ForAppending, -2)
    a.write samenvoegbox
    a.write Chr(13) + Chr(10)
    a.Close 'sluiten van tekstbestand
End If
TextBox1 = Clear
TextBox2 = Clear

 'lijst rangschikken
  Dim Veld(0 To 500)
  Dim textstring2 As String
  
    For I = 0 To ListBox1.ListCount - 1
    textstring2 = ListBox1.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox1.Clear
 
  For x = 0 To UBound(Veld)
  If Veld(x) <> "" Then ListBox1.AddItem Veld(x)
  Next x
ListBox1.SetFocus

  End Sub
Private Sub TextBox1_Change()
'Dim ab As String
'ab = TextBox1.Text
'ab =
TextBox1 = StrConv(TextBox1, vbProperCase)
If TextBox1 <> "" Then CommandButton1.Enabled = True
If TextBox1 = "" Then CommandButton1.Enabled = False
End Sub
Private Sub ListBox1_DblClick(ByVal Cancel As MSForms.ReturnBoolean)
ListBox1.MatchEntry = fmMatchEntryFirstLetter
Call plaatstekst
End Sub
Private Sub txtplaats_Click()
Call plaatstekst
End Sub
Sub plaatstekst()
On Error Resume Next
Call Schaal(scaal)
Dim returnpnt As Variant
Dim textobj As AcadText
Dim layerObj As AcadLayer
Set laagoud = ThisDrawing.ActiveLayer
Set layerObj = ThisDrawing.Layers.Add("RUIMTENAAM")
ThisDrawing.ActiveLayer = layerObj
If TextBox1 <> "" Then
waarde1 = TextBox1 'de waarde invullen van de textbox
Else
waarde1 = ListBox1.Value 'de waarde invullen van listbox1
End If
frmRuimtenaam.Hide 'het formulier verbergen
returnpnt = ThisDrawing.Utility.GetPoint(, "Geef begin punt op : ") 'beginpun opgeven

If Err Then
    frmRuimtenaam.Show
    Exit Sub
    End If
textobj.Alignment = returnpnt.acAlignmentCenter
Set textobj = ThisDrawing.ModelSpace.AddText(waarde1, returnpnt, scaal) 'text plaatsen

ThisDrawing.ActiveLayer = laagoud
Update
TextBox1 = ""
frmRuimtenaam.Show
End Sub
Sub uitlezenTXT()
bestand10 = "g:\tekeningen\ruimtenaam.txt"
Const ForReading = 1, ForWriting = 2, ForAppending = 8
Const TristateUseDefault = -2, TristateTrue = -1, TristateFalse = 0

Dim fs, a, vullistbox1
Set fs = CreateObject("Scripting.FileSystemObject")
Set a = fs.OpenTextFile(bestand10, ForReading, False)


Do While a.AtEndOfLine <> True
    vullistbox1 = a.ReadLine
    ListBox1.AddItem (vullistbox1)
Loop
a.Close 'sluiten van tekstbestand

  'lijst rangschikken
  Dim Veld(0 To 500)
  Dim textstring2 As String
  
    For I = 0 To ListBox1.ListCount - 1
    textstring2 = ListBox1.List(I)
    Veld(I) = textstring2
   
   Dim LB&, UB&, TEMP$, Pos&, x&
 
    LB = LBound(Veld)
    UB = UBound(Veld)
 
    While UB > LB
      Pos = LB
 
      For x = LB To UB - 1
        If Veld(x) > Veld(x + 1) Then
          TEMP = Veld(x + 1)
          Veld(x + 1) = Veld(x)
          Veld(x) = TEMP
          Pos = x
        End If
      Next x
 
      UB = Pos
    Wend
    
  Next I
  ListBox1.Clear
 
  For x = 0 To UBound(Veld)
  If Veld(x) <> "" Then ListBox1.AddItem Veld(x)
  Next x
End Sub
Sub Schaal(scaal)
frmRuimtenaam.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 30
Else
    scaal = 15
End If
If vartab(0) >= 16715 And vartab(0) <= 16725 Or vartab(0) >= 23575 And vartab(0) <= 23585 _
    Or vartab(0) >= 31375 And vartab(0) <= 31385 Then
    scaal = 60
End If
Update
End Sub
Private Sub cmdAfsluiten_Click()
Unload Me
End Sub

Attribute VB_Name = "frmSplitsen"
Attribute VB_Base = "0{C37085AE-AD26-4A0E-8CA8-65C7910F4816}{16F90DA4-E972-4BB0-88BA-40AA628A4628}"
Attribute VB_GlobalNameSpace = False
Attribute VB_Creatable = False
Attribute VB_PredeclaredId = True
Attribute VB_Exposed = False
Attribute VB_TemplateDerived = False
Attribute VB_Customizable = False

'Opsplitsen van rollengtes
'Michel Bosch en Gerard Haak

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If

Dim newLayer As AcadLayer
Set newLayer = ThisDrawing.Layers.Add("OPSPLITSEN")
ThisDrawing.ActiveLayer = newLayer
Update
Call combolijst1
Call Combolijst2
OptionButton1.Value = True
End Sub
Private Sub CancelButton1_Click()
frmSplitsen.Hide
Unload Me
End Sub
Private Sub CmdButton_Click()

 If ComboBox1 = ComboBox2 Then
 Label5 = "Groepsnummers mogen niet gelijk zijn"
 Label5.BackColor = &HFFFF&
 Exit Sub
 End If

teller = ListBox2.ListCount
CmdButton2.Enabled = True
If OptionButton1 = True Then D = " (WTH-ZD) "
If OptionButton2 = True Then D = " (PE-RT) "
C = "1 rol van " & ComboBox3 & " opsplitsen t.b.v. " & "Groep " & ComboBox1 & " en " & "Groep " & ComboBox2 & D
t = "1 rol van " & ComboBox3 & " opsplitsen t.b.v. " & "Groep " & ComboBox2 & " en " & "Groep " & ComboBox1 & D
e = "Groep " & ComboBox1 & " en " & "Groep " & ComboBox2
f = "Groep " & ComboBox2 & " en " & "Groep " & ComboBox1


For I = 0 To teller - 1
textstring = ListBox2.List(I)
If e = textstring Or f = textstring Then
 Label5 = "Deze combinatie heb je al gebruikt"
 Label5.BackColor = &HFFFF&
 Exit Sub
 End If
 Next I

ListBox1.AddItem C
ListBox2.AddItem e
ComboBox1.Text = ComboBox1.List(0)
ComboBox2.Text = ComboBox2.List(0)
Label5 = Clear
Label5.BackColor = &HC0C0C0
End Sub
Private Sub CmdButton1_Click()
frmSplitsen.Hide
End Sub
Private Sub CmdButton2_Click()
  On Error Resume Next
    Dim textobj As AcadText
    Dim textstring As String
    Dim pecht(0 To 2) As Double
    Dim pb0(0 To 2) As Double
    frmSplitsen.Hide
    ThisDrawing.SetVariable "osmode", 0
    pbzero = ThisDrawing.Utility.GetPoint(, "Plaats beginpunt") '---
    teller = ListBox1.ListCount
    omhoog = teller * 30
    
    Dim pb1(0 To 2) As Double
    
     pb1(0) = pbzero(0) - 910
     pb1(1) = pbzero(1) + (omhoog + 30)
     pb1(2) = pbzero(2)
    'pb1 = ThisDrawing.Utility.GetPoint(, "Plaats beginpunt")
    
  If Err Then
    frmSplitsen.Show
    Exit Sub
  End If
     
     pb0(0) = pb1(0)
     pb0(1) = pb1(1)
     pb0(2) = pb1(2)
   
    For I = 0 To teller - 1
    'Define the text object
    textstring = ListBox1.List(I)
     
     pecht(0) = pb1(0)             'Point(pBegin.pX, PY)
     pecht(1) = pb1(1) - 30
     pecht(2) = pb1(2)
       
     Set textobj = ThisDrawing.ModelSpace.AddText(textstring, pecht, 14.5)
     pb1(0) = pecht(0)             'Point(pBegin.pX, PY)
     pb1(1) = pecht(1)
     pb1(2) = pecht(2)

    Next I
    Update
    ' Create the text object in model space
    ZoomAll


 Dim LijnObj As AcadPolyline
' Dim Lijnobj As Object
 Dim pb2(0 To 2) As Double 'punt van rechthoek
 Dim pb3(0 To 2) As Double 'punt van rechthoek
 Dim pb4(0 To 2) As Double 'punt van rechthoek
 Dim pb5(0 To 2) As Double 'punt voor regelunittekst
 
 pb2(0) = pb0(0) - 15
 pb2(1) = pb0(1) + 15
 pb2(2) = 0
 
 pb3(0) = pb2(0) + 925
 pb3(1) = pb2(1)
 pb3(2) = 0
 
 pb4(0) = pb3(0)
 pb4(1) = pecht(1) - 30
 pb4(2) = 0
 
 pb5(0) = pb2(0)
 pb5(1) = pb4(1)
 pb5(2) = 0
   
Dim points(0 To 14) As Double
points(0) = pb2(0): points(1) = pb2(1): points(2) = pb2(2)
points(3) = pb3(0): points(4) = pb3(1): points(5) = pb3(2)
points(6) = pb4(0): points(7) = pb4(1): points(8) = pb4(2)
points(9) = pb5(0): points(10) = pb5(1): points(11) = pb5(2)
points(12) = pb2(0): points(13) = pb2(1): points(14) = pb2(2)
 
 Set LijnObj = ThisDrawing.ModelSpace.AddPolyline(points)
 LijnObj.Offset (3)
 LijnObj.Update
End Sub

Private Sub CmdButton3_Click()
ListBox1.Clear
ListBox2.Clear
CmdButton2.Enabled = False
ComboBox1.Text = ComboBox1.List(0)
ComboBox2.Text = ComboBox2.List(0)
Label5 = Clear
Label5.BackColor = &HC0C0C0
End Sub
Private Sub CmdButton4_Click()
    'Ensure ListBox contains list items
    ListBox2.ListIndex = ListBox1.ListIndex
    If ListBox1.ListCount >= 1 And ListBox2.ListCount >= 1 Then
        'If no selection, choose last list item.
        If ListBox1.ListIndex = -1 And ListBox2.ListCount >= -1 Then
            ListBox1.ListIndex = _
                     ListBox1.ListCount - 1
            ListBox2.ListIndex = _
                     ListBox2.ListCount - 1
        End If
        ListBox1.RemoveItem (ListBox1.ListIndex)
        ListBox2.RemoveItem (ListBox2.ListIndex)
    End If
End Sub
Private Sub ComboBox1_DropButtonClick()
 ComboBox1.SetFocus
 Label5 = Clear
 Label5.BackColor = &HC0C0C0
 End Sub
Private Sub ComboBox1_Enter()
 ComboBox1.SetFocus
 Label5 = Clear
 Label5.BackColor = &HC0C0C0
End Sub
Private Sub ComboBox2_DropButtonClick()
 ComboBox2.SetFocus
 Label5 = Clear
 Label5.BackColor = &HC0C0C0
End Sub

Private Sub ComboBox2_Enter()
 ComboBox2.SetFocus
 Label5 = Clear
 Label5.BackColor = &HC0C0C0
End Sub

Private Sub ComboBox3_Change()
  CmdButton.SetFocus
End Sub
Private Sub OptionButton1_Click()
Call Combolijst3
End Sub

Private Sub OptionButton2_Click()
Call combolijst4
End Sub

Sub combolijst1()
ComboBox1.AddItem "01.01"
ComboBox1.AddItem "02.01"
ComboBox1.AddItem "03.01"
ComboBox1.AddItem "04.01"
ComboBox1.AddItem "05.01"
ComboBox1.AddItem "06.01"
ComboBox1.AddItem "07.01"
ComboBox1.AddItem "08.01"
ComboBox1.AddItem "09.01"
ComboBox1.AddItem "10.01"
ComboBox1.Text = ComboBox1.List(0)
End Sub
Sub Combolijst2()
ComboBox2.AddItem "01.01"
ComboBox2.AddItem "02.01"
ComboBox2.AddItem "03.01"
ComboBox2.AddItem "04.01"
ComboBox2.AddItem "05.01"
ComboBox2.AddItem "06.01"
ComboBox2.AddItem "07.01"
ComboBox2.AddItem "08.01"
ComboBox2.AddItem "09.01"
ComboBox2.AddItem "10.01"
ComboBox2.Text = ComboBox2.List(0)
End Sub
Sub Combolijst3()
ComboBox3.Clear
ComboBox3.AddItem "125 meter"
ComboBox3.AddItem "105 meter"
ComboBox3.AddItem "90 meter"
ComboBox3.AddItem "75 meter"
ComboBox3.AddItem "63 meter"
ComboBox3.AddItem "50 meter"
ComboBox3.AddItem "40 meter"
ComboBox3.Text = ComboBox3.List(0)
End Sub
Sub combolijst4()
ComboBox3.Clear
ComboBox3.AddItem "120 meter"
ComboBox3.AddItem "90 meter"
ComboBox3.Text = ComboBox3.List(0)
End Sub

Attribute VB_Name = "frmVloermuur"
Attribute VB_Base = "0{8F4285CA-C5FD-4E0C-8D7B-A242257DD699}{E0F2707B-9167-4BDA-BBD1-D5F40C30FF4D}"
Attribute VB_GlobalNameSpace = False
Attribute VB_Creatable = False
Attribute VB_PredeclaredId = True
Attribute VB_Exposed = False
Attribute VB_TemplateDerived = False
Attribute VB_Customizable = False


'10-09-2002 Plaatsen van vloer of muursparing
'M.Bosch en G.C.Haak
'blmuur.dwg en bl-vloerspar


#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub OKButton1_Click()
On Error Resume Next
Dim newLayer As AcadLayer
Set newLayer = ThisDrawing.Layers.Add("3")
ThisDrawing.ActiveLayer = newLayer
Update
ThisDrawing.SetVariable "osmode", 0

Dim teller As Integer
Dim element As Object
frmVloermuur.Hide
If OptionButton1.Value = True Then
Call Schaal(scaal)
pbegin = ThisDrawing.Utility.GetPoint(, "Plaats punt -Blok Muursparing-")
Dim bestand As String
bestand = "C:\ACAD2002\DWG\blmuur.dwg"
Set blockRefObj = ThisDrawing.ModelSpace.InsertBlock(pbegin, bestand, scaal, scaal, 1, 0)
For Each element In ThisDrawing.ModelSpace
      If element.ObjectName = "AcDbBlockReference" Then
      If element.Name = "BLMUUR" Or "blmuur" Then
      Set symbool = element
        If symbool.HasAttributes Then
        attributen = symbool.GetAttributes
        For I = LBound(attributen) To UBound(attributen)
        Set attribuut = attributen(I)
        If TextBox1 = 1 Then w1 = "Muursparing 10 * 5 cm"
        If TextBox1 = 2 Then w1 = "Muursparing 15 * 5 cm"
        If TextBox1 = 3 Then w1 = "Muursparing 25 * 5 cm"
        If TextBox1 = 4 Then w1 = "Muursparing 30 * 5 cm"
        If TextBox1 = 5 Then w1 = "Muursparing 35 * 5 cm"
        If TextBox1 = 6 Then w1 = "Muursparing 45 * 5 cm"
        If TextBox1 = 7 Then w1 = "Muursparing 50 * 5 cm"
        If TextBox1 = 8 Then w1 = "Muursparing 60 * 5 cm"
        If TextBox1 = 9 Then w1 = "Muursparing 65 * 5 cm"
        If TextBox1 = 10 Then w1 = "Muursparing 75 * 5 cm"
        If TextBox1 = 11 Then w1 = "Muursparing 80 * 5 cm"
        If TextBox1 = 12 Then w1 = "Muursparing 85 * 5 cm"
        If TextBox1 = 13 Then w1 = "Muursparing 95 * 5 cm"
        If TextBox1 = 14 Then w1 = "Muursparing 100 * 5 cm"
        If TextBox1 = 15 Then w1 = "Muursparing 105 * 5 cm"
        If TextBox1 = 16 Then w1 = "Muursparing 115 * 5 cm"
        If TextBox1 = 17 Then w1 = "Muursparing 120 * 5 cm"
        If TextBox1 = 18 Then w1 = "Muursparing 130 * 5 cm"
        If TextBox1 = 19 Then w1 = "Muursparing 135 * 5 cm"
        If TextBox1 = 20 Then w1 = "Muursparing 145 * 5 cm"
        If attribuut.TagString = "MUURSPARING" And attribuut.textstring = "" Then attribuut.textstring = w1
        Next I
        End If
      End If
      End If
  Next element
  End If
Update

If OptionButton2.Value = True Then
Call Schaal(scaal)
pbegin = ThisDrawing.Utility.GetPoint(, "Plaats punt -Blok Vloersparing-")
Dim bestand2 As String
bestand2 = "C:\ACAD2002\DWG\bl-vloerspar.dwg"
Set blockRefObj = ThisDrawing.ModelSpace.InsertBlock(pbegin, bestand2, scaal, scaal, 1, 0)
For Each element In ThisDrawing.ModelSpace
      If element.ObjectName = "AcDbBlockReference" Then
      If element.Name = "SPARING" Or "sparing" Or "ETAGE" Or "etage" Then
      Set symbool = element
        If symbool.HasAttributes Then
        attributen = symbool.GetAttributes
        For I = LBound(attributen) To UBound(attributen)
        Set attribuut = attributen(I)
        If TextBox2 = 1 Then w2 = "Vloersparing 10 * 10 cm"
        If TextBox2 = 2 Then w2 = "Vloersparing 15 * 10 cm"
        If TextBox2 = 3 Then w2 = "Vloersparing 25 * 10 cm"
        If TextBox2 = 4 Then w2 = "Vloersparing 30 * 10 cm"
        If TextBox2 = 5 Then w2 = "Vloersparing 35 * 10 cm"
        If TextBox2 = 6 Then w2 = "Vloersparing 45 * 10 cm"
        If TextBox2 = 7 Then w2 = "Vloersparing 50 * 10 cm"
        If TextBox2 = 8 Then w2 = "Vloersparing 60 * 10 cm"
        If TextBox2 = 9 Then w2 = "Vloersparing 65 * 10 cm"
        If TextBox2 = 10 Then w2 = "Vloersparing 75 * 10 cm"
        If TextBox2 = 11 Then w2 = "Vloersparing 80 * 10 cm"
        If TextBox2 = 12 Then w2 = "Vloersparing 85 * 10 cm"
        If TextBox2 = 13 Then w2 = "Vloersparing 95 * 10 cm"
        If TextBox2 = 14 Then w2 = "Vloersparing 100 * 10 cm"
        If TextBox2 = 15 Then w2 = "Vloersparing 105 * 10 cm"
        If TextBox2 = 16 Then w2 = "Vloersparing 115 * 10 cm"
        If TextBox2 = 17 Then w2 = "Vloersparing 120 * 10 cm"
        If TextBox2 = 18 Then w2 = "Vloersparing 130 * 10 cm"
        If TextBox2 = 19 Then w2 = "Vloersparing 135 * 10 cm"
        If TextBox2 = 20 Then w2 = "Vloersparing 145 * 10 cm"
        If attribuut.TagString = "ETAGE" And attribuut.textstring = "" Then attribuut.textstring = ComboBox1
        If attribuut.TagString = "SPARING" And attribuut.textstring = "" Then attribuut.textstring = w2
        Next I
        End If
      End If
      End If
  Next element
  End If
Update

TextBox1.Value = Clear
TextBox2.Value = Clear
ComboBox1.Text = ComboBox1.List(2)
If OptionButton1.Value = True Then TextBox1.SetFocus
If OptionButton2.Value = True Then TextBox2.SetFocus

If Err Then
    If OptionButton1.Value = True Then TextBox1.SetFocus
    If OptionButton2.Value = True Then TextBox2.SetFocus
    frmVloermuur.Show
    Exit Sub
    End If
Update
End Sub

Private Sub OptionButton1_Click()
If OptionButton1.Value = True Then
  TextBox1.Visible = True
  TextBox1.SetFocus
  OptionButton2.Value = False
  TextBox2.Visible = False
  ComboBox1.Visible = False
  Label1.Visible = False
  'AcPreview1.Preview = "C:\ACAD2002\DWG\blmuur" & ".dwg"
  End If
  
End Sub
Private Sub OptionButton2_Click()
If OptionButton2.Value = True Then
  OptionButton1.Value = False
  TextBox2.Visible = True
  TextBox1.Visible = False
  TextBox2.SetFocus
  ComboBox1.Visible = True
  Label1.Visible = True
  Call combolijst
  End If
End Sub
Private Sub ResetButton1_Click()
Call RESET
End Sub
  Sub RESET()
   OptionButton1.Value = False: OptionButton2.Value = False
   ComboBox1.Visible = False
   OKButton1.Enabled = False
   Label1.Visible = False
   TextBox1.Visible = False: TextBox2.Visible = False
  End Sub
Private Sub TextBox1_Change()
Dim a As Double
On Error Resume Next
If TextBox1.Value <> "" Then OKButton1.Enabled = True Else OKButton1.Enabled = False
a = TextBox1.Text

If Err Then
   TextBox1.Text = Clear
   Exit Sub
  End If
  
If a > 20 Then
   MsgBox "Groter dan 20 groepen is niet toegestaan..!!!!", vbCritical
   TextBox1 = Clear
End If
  
If a < 1 Then
   MsgBox "Kleiner dan een 1 groeps muurparing is niet mogelijk..!!!!", vbCritical
   TextBox1 = Clear
End If
  
End Sub

Private Sub TextBox2_Change()
Dim b As Double
On Error Resume Next
If TextBox2.Value <> "" Then OKButton1.Enabled = True Else OKButton1.Enabled = False
b = TextBox2.Text
If Err Then
   TextBox2.Text = Clear
   Exit Sub
  End If
  
If b > 20 Then
   MsgBox "Groter dan 20 groepen is niet toegestaan..!!!!", vbCritical
   TextBox2 = Clear
End If
End Sub
Private Sub UserForm_Initialize()
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
frmVloermuur.TextBox1.SetFocus
  End Sub
   Sub combolijst()
   ComboBox1.AddItem "in de kruipruimte."
   ComboBox1.AddItem "in de leidingkoker."
   ComboBox1.AddItem "op de begane grond."
   ComboBox1.AddItem "op de 1e Verdieping."
   ComboBox1.AddItem "op de 2e Verdieping."
   ComboBox1.AddItem "op de 3e Verdieping."
   ComboBox1.AddItem "op de 4e Verdieping."
   ComboBox1.AddItem "op de zolder."
   ComboBox1.AddItem "in de kelder."
   'ComboBox1.Text = ComboBox1.List(2)
   ComboBox1.MatchEntry = fmMatchEntryFirstLetter
  End Sub
Sub Schaal(scaal)
frmVloermuur.Hide
On Error Resume Next
vartab = ThisDrawing.GetVariable("EXTMAX")
If vartab(0) >= 2145 And vartab(0) <= 2155 Or vartab(0) >= 4095 And vartab(0) <= 4105 _
    Or vartab(0) >= 5835 And vartab(0) <= 5845 Or vartab(0) >= 8355 And vartab(0) <= 8365 _
    Or vartab(0) >= 11785 And vartab(0) <= 11795 Or vartab(0) >= 15685 And vartab(0) <= 15695 Then
    scaal = 2
Else
    scaal = 1
End If
If vartab(0) >= 16715 And vartab(0) <= 16725 Or vartab(0) >= 23575 And vartab(0) <= 23585 _
    Or vartab(0) >= 31375 And vartab(0) <= 31385 Then
    scaal = 4
End If
Update
End Sub

Private Sub CancelButton1_Click()
frmVloermuur.Hide
Unload Me
' ThisDrawing.SetVariable "osmode" = Z
End Sub

Private Sub CommandButton1_Click()
Unload Me
ThisDrawing.SendCommand "arrow" & vbCr
End Sub

Attribute VB_Name = "frmbouwtek"
Attribute VB_Base = "0{6C380B06-766A-4FA6-B1CB-C0617CC1DD97}{B34D0C81-333B-4B20-B4EA-BF4C7F1BF2A4}"
Attribute VB_GlobalNameSpace = False
Attribute VB_Creatable = False
Attribute VB_PredeclaredId = True
Attribute VB_Exposed = False
Attribute VB_TemplateDerived = False
Attribute VB_Customizable = False

#If VBA7 Then
    Private Declare PtrSafe Function FindWindow Lib "user32" Alias "FindWindowA" ( _
        ByVal lpClassName As String, ByVal lpWindowName As String) As LongPtr

    Private Declare PtrSafe Function DrawMenuBar Lib "user32" ( _
        ByVal hWnd As LongPtr) As Long

    Private Declare PtrSafe Function GetMenuItemCount Lib "user32" ( _
        ByVal hMenu As LongPtr) As Long

    Private Declare PtrSafe Function GetSystemMenu Lib "user32" ( _
        ByVal hWnd As LongPtr, ByVal bRevert As Long) As LongPtr

    Private Declare PtrSafe Function RemoveMenu Lib "user32" ( _
        ByVal hMenu As LongPtr, ByVal nPosition As Long, ByVal wFlags As Long) As Long
#Else
    Private Declare Function FindWindow Lib "user32" Alias "FindWindowA" ( _
        ByVal lpClassName As String, ByVal lpWindowName As String) As Long

    Private Declare Function DrawMenuBar Lib "user32" ( _
        ByVal hWnd As Long) As Long

    Private Declare Function GetMenuItemCount Lib "user32" ( _
        ByVal hMenu As Long) As Long

    Private Declare Function GetSystemMenu Lib "user32" ( _
        ByVal hWnd As Long, ByVal bRevert As Long) As Long

    Private Declare Function RemoveMenu Lib "user32" ( _
        ByVal hMenu As Long, ByVal nPosition As Long, ByVal wFlags As Long) As Long
#End If

Private Const MF_BYPOSITION = &H400
Private Const MF_REMOVE = &H1000
Private Sub UserForm_Initialize()
'begin sluiten toets uitschakelen
#If VBA7 Then
    Dim lngHwnd As LongPtr
    Dim lngMenu As LongPtr
#Else
    Dim lngHwnd As Long
    Dim lngMenu As Long
#End If
  Dim lngCnt As Long
  lngHwnd = FindWindow(vbNullString, Me.Caption)
  lngMenu = GetSystemMenu(lngHwnd, 0)
  If lngMenu Then
    lngCnt = GetMenuItemCount(lngMenu)
    Call RemoveMenu(lngMenu, lngCnt - 1, _
    MF_REMOVE Or MF_BYPOSITION)
    Call DrawMenuBar(lngHwnd)
  End If
'einde sluiten toets uitschakelen
frmbouwtek.TextBox1.SetFocus

End Sub
Private Sub CancelButton_Click()

If (frmbouwtek.TextBox1 <> "" And frmbouwtek.TextBox1.TextLength < 2) Or frmbouwtek.TextBox1 > "31" Then
    MsgBox "Je moet minimaal 2 getallen invoeren.. (Aantal dagen van de maand)" & (Chr(13) & Chr(10)) & (Chr(13) & Chr(10)) & _
           "Dit moet een getal zijn die ligt tussen  0 en 32 " & (Chr(13) & Chr(10)) & _
           "Voor de getallen 1 tot en met 9 een nul vermelden.", vbExclamation
    frmbouwtek.TextBox1 = Clear
    frmbouwtek.TextBox1.SetFocus
    Exit Sub
End If

If (frmbouwtek.TextBox3 <> "" And frmbouwtek.TextBox3.TextLength < 2) Or frmbouwtek.TextBox3 > "12" Then
    MsgBox "Je moet minimaal 2 getallen invoeren.. (Aantal maanden van het jaar)" & (Chr(13) & Chr(10)) & (Chr(13) & Chr(10)) & _
           "Dit moet een getal zijn die ligt tussen  0 en 13" & (Chr(13) & Chr(10)) & _
           "Voor de getallen 1 tot en met 9 een nul vermelden.", vbExclamation
    frmbouwtek.TextBox3 = Clear
    frmbouwtek.TextBox3.SetFocus
    Exit Sub
End If

If frmbouwtek.TextBox4 <> "" And frmbouwtek.TextBox4.TextLength < 4 Then
    MsgBox "Je moet minimaal 4 getallen invoeren..(Jaartal)", vbExclamation
    frmbouwtek.TextBox4 = Clear
    frmbouwtek.TextBox4.SetFocus
    Exit Sub
End If



If frmbouwtek.TextBox1 <> "" And frmbouwtek.TextBox2 <> "" And frmbouwtek.TextBox3 <> "" And frmbouwtek.TextBox4 <> "" Then
   blokken.TextBox19 = frmbouwtek.TextBox1 & "-" & frmbouwtek.TextBox3 & "-" & frmbouwtek.TextBox4  'datum
   blokken.TextBox20 = frmbouwtek.TextBox2 'naam
End If

If TextBox1 = "" Or TextBox2 = "" Or TextBox3 = "" Or TextBox4 = "" Then blokken.CheckBox1 = False
Unload Me
blokken.Show

End Sub
Private Sub TextBox1_Change()
On Error Resume Next
Dim b As Double

b = frmbouwtek.TextBox1
If Err Then
   frmbouwtek.TextBox1.Value = Clear
   Exit Sub
End If

If frmbouwtek.TextBox1.TextLength = 2 Then frmbouwtek.TextBox3.SetFocus


End Sub
Private Sub TextBox3_Change()
On Error Resume Next
Dim b As Double
b = frmbouwtek.TextBox3

If Err Then
   frmbouwtek.TextBox3.Value = Clear
   Exit Sub
End If

If frmbouwtek.TextBox3.TextLength = 2 Then frmbouwtek.TextBox4.SetFocus


End Sub
Private Sub TextBox4_Change()
On Error Resume Next
Dim b As Double

b = frmbouwtek.TextBox4
If Err Then
   frmbouwtek.TextBox4.Value = Clear
   Exit Sub
End If

If frmbouwtek.TextBox4.TextLength = 4 Then frmbouwtek.TextBox2.SetFocus


End Sub

Private Sub CommandButton1_Click()
frmbouwtek.TextBox1 = Clear: frmbouwtek.TextBox2 = Clear: frmbouwtek.TextBox3 = Clear: frmbouwtek.TextBox4 = Clear
frmbouwtek.TextBox1.SetFocus
End Sub
